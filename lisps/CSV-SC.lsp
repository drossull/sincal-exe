;;; CSV-SC -- Informe de armaduras Tekla CSV/XSR -> tabla nativa editable.
;;; No convierte unidades, agrupa marcas ni recalcula el total declarado.
(vl-load-com)

(defun SCSV:Fail (msg) (princ (strcat "\nCSV-SC: " msg)) (exit))
(defun SCSV:Trim (s) (vl-string-trim " \t\r\n" s))
(defun SCSV:Digits (s)
  (and (/= s "") (not (wcmatch s "*[~0-9]*"))))

;;; CSV con ;, campos vacios, comillas y comillas dobles escapadas.
;;; Rechaza comillas sin cerrar; no interpreta expresiones ni formulas.
(defun SCSV:Fields (line / i ch quoted closed value fields)
  (setq i 1 value "")
  (while (<= i (strlen line))
    (setq ch (substr line i 1))
    (cond
      ((= ch "\"")
       (cond
         ((and quoted (= (substr line (1+ i) 1) "\""))
          (setq value (strcat value "\"") i (1+ i)))
         (quoted (setq quoted nil closed T))
         ((and (not closed) (= (SCSV:Trim value) "")) (setq quoted T value ""))
         (T (SCSV:Fail "Comillas inesperadas en el CSV."))))
      ((and (= ch ";") (not quoted))
       (setq fields (cons (SCSV:Trim value) fields) value "" closed nil))
      ((and closed (not (member ch '(" " "\t" "\r"))))
       (SCSV:Fail "Hay texto despues de un campo entre comillas."))
      (T (setq value (strcat value ch)) ))
    (setq i (1+ i)))
  (if quoted (SCSV:Fail "Campo entre comillas sin cerrar (no se admiten campos multilinea)."))
  (reverse (cons (SCSV:Trim value) fields)))

;;; El archivo de ejemplo es ANSI. ADODB permite tambien UTF-8 sin cambiar LISPSYS.
;;; El objeto se libera incluso si falla la lectura.
(defun SCSV:ReadText (path charset / stream result)
  (setq stream (vlax-create-object "ADODB.Stream"))
  (setq result (vl-catch-all-apply
    '(lambda ()
       (vlax-put-property stream 'Type 2)
       (vlax-put-property stream 'Charset charset)
       (vlax-invoke-method stream 'Open nil nil nil nil nil)
       (vlax-invoke-method stream 'LoadFromFile path)
       (vlax-invoke-method stream 'ReadText -1))))
  (vl-catch-all-apply 'vlax-invoke-method (list stream 'Close))
  (vlax-release-object stream)
  (if (vl-catch-all-error-p result)
    (SCSV:Fail (strcat "No se pudo leer el archivo: " (vl-catch-all-error-message result))))
  result)

(defun SCSV:Lines (s / p lines)
  (while (setq p (vl-string-search "\n" s))
    (setq lines (cons (substr s 1 p) lines) s (substr s (+ p 2))))
  (reverse (cons s lines)))

(defun SCSV:HeaderP (cells)
  (and (= (length cells) 16)
       (= (strcase (car cells)) "CANT.")
       (= (strcase (nth 3 cells)) "POS")
       (= (strcase (nth 5 cells)) "FORMA")))

(defun SCSV:ParseDelimited (text / line cells header rows total lineNo)
  (setq lineNo 0)
  (foreach line (SCSV:Lines text)
    (setq lineNo (1+ lineNo) line (SCSV:Trim line))
    (cond
      ((or (= line "") (not (wcmatch line "*[~-]*"))))
      (T
       (setq cells (SCSV:Fields line))
       (cond
         ((SCSV:HeaderP cells)
          (if (and header (not (equal header cells)))
            (SCSV:Fail "Los encabezados de las paginas no coinciden."))
          (setq header cells))
         ((and header (SCSV:Digits (car cells)))
          (if (or total (/= (length cells) 16))
            (SCSV:Fail (strcat "Fila invalida o posterior al total, linea " (itoa lineNo) ".")))
          (setq rows (cons cells rows)))
         ((and header (>= (length cells) 9) (= (strcase (nth 6 cells)) "TOTAL"))
          (if total (SCSV:Fail "Hay mas de un total; revise el archivo."))
          ;; kg es una unidad del peso, NO un dato de la columna A max.
          (setq total (list (nth 7 cells) (nth 8 cells))))
         ((or (wcmatch (strcase line) "LISTADO DE ARMADURAS*,MODELO:*")
              (and (= (car cells) "")
                   (or (= (SCSV:Trim (apply 'strcat cells)) "")
                       (wcmatch (strcase (SCSV:Trim (apply 'strcat cells)))
                                "FECHA:*,HORA:*,DIMENSIONES*,P*GINA:*")))))
         (T (SCSV:Fail (strcat "Contenido no reconocido en linea " (itoa lineNo) ". No se importo parcialmente.")))))))
  (if (or (not header) (not rows)) (SCSV:Fail "No hay encabezado y filas de armaduras validos."))
  (list header (reverse rows) total))

(defun SCSV:Words (s / i ch word words)
  (setq i 1 word "")
  (while (<= i (strlen s))
    (setq ch (substr s i 1))
    (if (member ch '(" " "\t" "\r"))
      (if (/= word "") (setq words (cons word words) word ""))
      (setq word (strcat word ch)))
    (setq i (1+ i)))
  (if (/= word "") (setq words (cons word words)))
  (reverse words))

;;; Posiciones 0-based de los titulos separados por dos o mas espacios.
;;; Los espacios simples en A max / TOTAL MIN pertenecen al titulo.
(defun SCSV:Spans (line / i start spans)
  (setq i 0)
  (while (< i (strlen line))
    (while (and (< i (strlen line)) (= (substr line (1+ i) 1) " ")) (setq i (1+ i)))
    (if (< i (strlen line))
      (progn
        (setq start i)
        (while (and (< i (strlen line)) (/= (substr line (1+ i) 2) "  ")) (setq i (1+ i)))
        (setq spans (cons (list start i (SCSV:Trim (substr line (1+ start) (- i start)))) spans)))))
  (reverse spans))

(defun SCSV:FixedCells (line cuts / cells start finish)
  (setq start (car cuts) cuts (cdr cuts))
  (foreach finish cuts
    (setq cells (cons (SCSV:Trim (substr line (1+ start) (- finish start))) cells) start finish))
  (reverse (cons (SCSV:Trim (substr line (1+ start))) cells)))

(defun SCSV:ParseFixed (text / lines line trimmed words header spans rows total cuts gaps i stop blank candidate span cells result)
  (setq lines (SCSV:Lines text))
  (foreach line lines
    (setq trimmed (SCSV:Trim line) words (SCSV:Words trimmed))
    (cond
      ((or (= trimmed "") (not (wcmatch trimmed "*[~-]*"))))
      ((wcmatch (strcase trimmed) "CANT.*")
       (if (and header (/= line header)) (SCSV:Fail "Encabezados XSR incompatibles entre paginas."))
       (setq header line spans (SCSV:Spans line)))
      ((and header (SCSV:Digits (car words)))
       (if total (SCSV:Fail "Hay filas XSR despues del total."))
       (setq rows (cons line rows)))
      ((and header (= (strcase (car words)) "TOTAL"))
       (if (or total (/= (length words) 3)) (SCSV:Fail "Total XSR no reconocido."))
       (setq total (cdr words)))
      ((wcmatch (strcase trimmed) "LISTADO DE ARMADURAS*,MODELO:*,FECHA:*,HORA:*,DIMENSIONES*,P*GINA:*"))
      (T (SCSV:Fail "Linea XSR no reconocida. No se importo parcialmente."))))
  (if (or (not rows) (not (SCSV:HeaderP (mapcar 'caddr spans))))
    (SCSV:Fail "El XSR no contiene el listado de armaduras de 16 columnas esperado."))
  ;; Buscar separaciones que esten vacias en TODAS las filas. No dividir por
  ;; palabras: eso desplazaria B/C cuando una dimension no tiene valor.
  (setq gaps spans cuts '(0))
  (while (cdr gaps)
    (setq i (cadar gaps) stop (caadr gaps) candidate nil)
    (while (< i stop)
      (setq blank T)
      (foreach line rows
        (if (not (member (substr line (1+ i) 1) '("" " "))) (setq blank nil)))
      (if blank (setq candidate i))
      (setq i (1+ i)))
    (if (not candidate) (SCSV:Fail "Columnas XSR superpuestas o truncadas; revise el informe."))
    (setq cuts (cons candidate cuts) gaps (cdr gaps)))
  (setq cuts (reverse cuts))
  (foreach line (reverse rows)
    (setq cells (SCSV:FixedCells line cuts))
    (if (or (not (SCSV:Digits (car cells))) (= (nth 14 cells) "") (= (nth 15 cells) ""))
      (SCSV:Fail "Fila XSR incompleta o truncada."))
    (setq result (cons cells result)))
  (list (mapcar 'caddr spans) (reverse result) total))

(defun SCSV:Parse (text / mode line)
  (foreach line (SCSV:Lines text)
    (if (wcmatch (strcase (SCSV:Trim line)) "CANT.*")
      (setq mode (if (vl-string-search ";" line) 'delimited 'fixed))))
  (cond ((eq mode 'delimited) (SCSV:ParseDelimited text))
        ((eq mode 'fixed) (SCSV:ParseFixed text))
        (T (SCSV:Fail "No se encontro el encabezado del listado CSV/XSR."))))

(defun SCSV:Master (/ path base)
  (foreach base (list (getenv "SINCAL_TEST_ROOT")
                     (if (getenv "LOCALAPPDATA") (strcat (getenv "LOCALAPPDATA") "/SINCAL/resources"))
                     (if (getenv "APPDATA") (strcat (getenv "APPDATA") "/Estandar SINCAL"))
                     (if (getenv "ProgramFiles") (strcat (getenv "ProgramFiles") "/SINCAL")))
    (if (and base (not path))
      (setq path (findfile (strcat base "/masters/FORMATOS ANOTATIVOS ACAD_2025.dwg")))))
  (if (not path) (setq path (findfile "FORMATOS ANOTATIVOS ACAD_2025.dwg")))
  (if (not path) (setq path (getfiled "Seleccione el master de formatos anotativos" "" "dwg" 0)))
  path)

(defun SCSV:Dbx (/ prog candidate db)
  (foreach prog (list (strcat "ObjectDBX.AxDbDocument." (substr (getvar "ACADVER") 1 2))
                     "ObjectDBX.AxDbDocument" "ZWCAD.ZcDbDocument")
    (if (not db)
      (progn
        (setq candidate (vl-catch-all-apply 'vla-GetInterfaceObject (list (vlax-get-acad-object) prog)))
        (if (not (vl-catch-all-error-p candidate)) (setq db candidate)))))
  db)

(defun SCSV:Style (doc / dict style path db result source objects)
  (setq dict (vla-Item (vla-get-Dictionaries doc) "ACAD_TABLESTYLE")
        style (vl-catch-all-apply 'vla-Item (list dict "TENSIONES")))
  (if (vl-catch-all-error-p style)
    (progn
      (setq path (SCSV:Master))
      (if (not path) (SCSV:Fail "No se selecciono el master."))
      (setq db (SCSV:Dbx))
      (if (not db) (SCSV:Fail "No se pudo iniciar ObjectDBX para leer el estilo del master."))
      (setq result (vl-catch-all-apply
        '(lambda ()
           (vla-Open db path)
           (setq source (vla-Item (vla-Item (vla-get-Dictionaries db) "ACAD_TABLESTYLE") "TENSIONES")
                 objects (vlax-make-safearray vlax-vbObject '(0 . 0)))
           (vlax-safearray-put-element objects 0 source)
           (vla-CopyObjects db objects dict))))
      (vlax-release-object db)
      (if (vl-catch-all-error-p result)
        (SCSV:Fail (strcat "No se pudo importar TENSIONES: " (vl-catch-all-error-message result))))
      (setq style (vla-Item dict "TENSIONES"))))
  style)

;;; Escapa control MText y campos CAD: el CSV siempre se muestra como texto literal.
(defun SCSV:Literal (s / i ch result)
  (setq i 1 result "")
  (while (<= i (strlen s))
    (setq ch (substr s i 1))
    (setq result (strcat result
      (cond ((member ch '("\\" "{" "}")) (strcat "\\" ch))
            ((= ch "%") "\\U+0025")
            (T ch))))
    (setq i (1+ i)))
  result)

(defun SCSV:Build (doc data point factor / style space table rows all row col widths value values height margin count)
  (setq style (SCSV:Style doc)
        height (vla-GetTextHeight style 1)
        margin (vla-get-HorzCellMargin style)
        rows (cadr data)
        all (cons (car data) rows)
        count (+ 2 (length rows) (if (caddr data) 1 0))
        space (if (= 1 (getvar "CVPORT")) (vla-get-PaperSpace doc) (vla-get-ModelSpace doc)))
  (setq table (vla-AddTable space (vlax-3d-point point) count 16
                (+ height (* 2 (vla-get-VertCellMargin style))) (+ (* height 8) (* 2 margin))))
  ;; SCSV:table pertenece al comando y permite limpiar fallos de construccion.
  (setq SCSV:table table)
  (vla-put-RegenerateTableSuppressed table :vlax-true)
  (vla-put-StyleName table "TENSIONES")
  (vla-put-TitleSuppressed table :vlax-false)
  (vla-put-HeaderSuppressed table :vlax-false)
  (vla-SetText table 0 0 "LISTADO DE ARMADURAS")
  (setq widths nil col 0)
  (repeat 16
    (setq count 0)
    (foreach row all (setq count (max count (strlen (nth col row)))))
    (setq widths (cons (+ (* height 0.85 (+ count 1)) (* 2 margin)) widths)
          col (1+ col)))
  (setq col 0)
  (foreach value (reverse widths)
    (vla-SetColumnWidth table col value) (setq col (1+ col)))
  (setq row 1)
  (foreach values all
    (setq col 0)
    (foreach value values
      ;; acString=4, acUnitless=0: conserva ceros, decimales y codigos del origen.
      (vla-SetCellDataType table row col 4 0)
      (vla-SetText table row col (SCSV:Literal value))
      (setq col (1+ col)))
    (setq row (1+ row)))
  (if (caddr data)
    (progn
      (vla-SetText table row 6 "Total")
      (vla-SetCellDataType table row 7 4 0)
      (setq value (strcat (car (caddr data)) " " (cadr (caddr data))))
      (vla-SetText table row 7 (SCSV:Literal value))
      (vla-SetColumnWidth table 7 (max (vla-GetColumnWidth table 7)
        (+ (* height 0.85 (1+ (strlen value))) (* 2 margin))))))
  (vla-put-RegenerateTableSuppressed table :vlax-false)
  ;; AddTable hereda alturas del estilo corriente anterior. Ajustarlas solo
  ;; despues de resolver las fuentes y el contenido del estilo TENSIONES.
  (setq row 0)
  (repeat (vla-get-Rows table)
    (vla-SetRowHeight table row (vla-GetMinimumRowHeight table row))
    (setq row (1+ row)))
  (if (/= factor 1.0) (vla-ScaleEntity table (vlax-3d-point point) factor))
  (vla-Update table)
  table)

(defun c:CSV-SC (/ *error* path encoding data point factor default doc begun SCSV:table)
  (defun *error* (msg)
    (if SCSV:table (vl-catch-all-apply 'vla-Delete (list SCSV:table)))
    (if begun (vla-EndUndoMark doc))
    (if (and msg (not (wcmatch (strcase msg) "*CANCEL*,*QUIT*,*BREAK*,*EXIT ABORT*")))
      (princ (strcat "\nCSV-SC: " msg)))
    (princ))
  (if (setq path (getfiled "Importar armaduras CSV o XSR" "" "" 132))
    (progn
      (if (not (member (strcase (vl-filename-extension path)) '(".CSV" ".XSR")))
        (SCSV:Fail "Seleccione un archivo .csv o .xsr."))
      (initget "ANSI UTF8")
      (setq encoding (getkword "\nCodificacion del archivo [ANSI/UTF8] <ANSI>: "))
      (setq data (SCSV:Parse (SCSV:ReadText path (if (= encoding "UTF8") "utf-8" "windows-1252"))))
      (princ (strcat "\n" (itoa (length (cadr data))) " filas, 16 columnas. Sin conversion de unidades."))
      (setq default (if (= 1 (getvar "CVPORT")) 1.0 (/ 1.0 (getvar "CANNOSCALEVALUE"))))
      (initget 6)
      (setq factor (getreal (strcat "\nFactor de tamano de la tabla <" (rtos default 2 6) ">: ")))
      (if (not factor) (setq factor default))
      (if (setq point (getpoint "\nEsquina superior izquierda de la tabla: "))
        (progn
          (setq doc (vla-get-ActiveDocument (vlax-get-acad-object)))
          (vla-StartUndoMark doc) (setq begun T)
          (SCSV:Build doc data (trans point 1 0) factor)
          (vla-EndUndoMark doc) (setq begun nil SCSV:table nil)
          (princ "\nTabla TENSIONES creada. Celdas editables; sin vinculo automatico al archivo.")))))
  (princ))
(princ)

;;; Authoring helper. Run only in a disposable COPY containing the RomanD style.
;;; Produces the native dynamic definition; never saves the source drawing.
(vl-load-com)
(defun SCMB:Mask (en / data before after pair inside)
  (foreach pair (entget en)
    (if (= (car pair) 101) (setq inside T))
    (if inside (setq after (append after (list pair)))
      (setq before (append before (list pair)))))
  (if (not after) (progn (princ "\nMissing embedded MText") (quit)))
  (setq after (vl-remove-if '(lambda (p) (member (car p) '(90 45 63 421 431))) after))
  (entmod (append before after '((90 . 3) (45 . 1.2) (63 . 256)))))
(defun SCMB:Attribute (tag value x centered)
  (entmake (list '(0 . "ATTDEF") '(8 . "0") '(62 . 3)
    (cons 10 (list x 0.0 0.0)) (cons 11 (list x 0.0 0.0))
    '(40 . 1.0) (cons 1 value) (cons 2 tag) (cons 3 tag) '(7 . "RomanD")
    '(70 . 0) (cons 72 (if centered 1 0)) '(74 . 2) '(280 . 1))))
(defun SCMB:Geometry (/ name obj en)
  (if (not (tblsearch "STYLE" "RomanD")) (progn (princ "\nRomanD is required") (quit)))
  (setq name (if SCMB:NewPresentation "SINCAL_MARCA_SC_V3" "SINCAL_MARCA_SC_V2"))
  (if (tblsearch "BLOCK" name) (progn (princ "\nDefinition already exists") (quit)))
  (entmake (list '(0 . "BLOCK") (cons 2 name) '(70 . 2) '(10 0.0 0.0 0.0)))
  (entmake '((0 . "CIRCLE") (8 . "0") (62 . 1) (10 0.0 0.0 0.0) (40 . 1.25)))
  (SCMB:Attribute "XX" "1" 0.0 T)
  (SCMB:Attribute "MARCA" "%%c8@20" 1.7 nil)
  (SCMB:Attribute "MARCA_CANT" "163 %%c8@20" 1.7 nil)
  (entmake '((0 . "ENDBLK")))
  (vlax-for obj (vla-item (vla-get-Blocks (vla-get-ActiveDocument (vlax-get-acad-object))) name)
    (if (= (vla-get-ObjectName obj) "AcDbAttributeDefinition")
      (progn
        (setq en (vlax-vla-object->ename obj))
        (vla-put-LockPosition obj :vlax-true)
        (if (/= (vla-get-TagString obj) "XX")
          (progn
            (vla-put-MTextAttribute obj :vlax-true)
            (vla-UpdateMTextAttribute obj)
            (SCMB:Mask en))))))
  (regapp "AcadAnnotative")
  (setq en (vlax-vla-object->ename (vla-item (vla-get-Blocks (vla-get-ActiveDocument (vlax-get-acad-object))) name)))
  (entmod (append (entget en)
    '((-3 ("AcadAnnotative" (1000 . "AnnotativeData") (1002 . "{") (1070 . 1) (1070 . 1) (1002 . "}"))))))
  name)
(defun SCMB:Build (/ name descriptions short long)
  (setq name (SCMB:Geometry))
  (setvar "OSMODE" 0) (setvar "MIRRTEXT" 0) (setvar "FILEDIA" 0)
  (setvar "BACTIONBARMODE" 1)
  (command "_.-BEDIT" name)
  (setq short (ssget "_X" '((0 . "ATTDEF") (2 . "MARCA")))
        long (ssget "_X" '((0 . "ATTDEF") (2 . "MARCA_CANT")))
        descriptions (ssget "_X" '((0 . "ATTDEF") (2 . "MARCA,MARCA_CANT"))))
  (command "_.BPARAMETER" "_Flip" '(0 -2 0) '(0 3 0) '(-2 -3 0) 1)
  (command "_.BACTION" '(0 2 0) descriptions "")
  (command "_.BPARAMETER" "_Visibility" '(2 3 0) 1)
  (command "_.-BVSTATE" "_New" "SIN_CANTIDAD" "_Show")
  (command "_.BVHIDE" long "" "_Current")
  (command "_.-BVSTATE" "_New" "CON_CANTIDAD" "_Show")
  (command "_.BVHIDE" short "" "_Current")
  (command "_.-BVSTATE" "_Delete" "VisibilityState0")
  (command "_.-BVSTATE" "_Set" "SIN_CANTIDAD")
  (if SCMB:NewPresentation (SCMB:States nil short long))
  (command "_.BSAVE")
  (command "_.BCLOSE")
  (princ "\nSCMB_BUILD_COMPLETE")
  (princ))

(defun SCMB:States (detail short long / base suffix suple state)
  (foreach base (if detail '("NORMAL") '("SIN_CANTIDAD" "CON_CANTIDAD"))
    (foreach suffix '("" "SUP" "INF")
      (foreach suple '("" "_SUPLE")
        (setq state (strcat (if (and detail (/= suffix "")) suffix base)
          (if (or detail (= suffix "")) "" (strcat "_" suffix)) suple))
        (if (or detail (/= state base))
          (progn
            (command "_.-BVSTATE" "_New" state "_Show")
            (if (not detail)
              (command "_.BVHIDE" (if (= base "CON_CANTIDAD") short long) "" "_Current")))))))
  (if detail (command "_.-BVSTATE" "_Delete" "VisibilityState0"))
  (command "_.-BVSTATE" "_Set" (if detail "NORMAL" "SIN_CANTIDAD")))

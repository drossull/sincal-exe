;;; Run after build_marca_sc.lsp in a disposable document with RomanD loaded.
;;; Reuses the SC circle, attribute authoring, masks and native flip workflow.
(defun SCMDB:Build (/ name obj en descriptions)
  (setq name (if SCMB:NewPresentation "SINCAL_MARCA_DE_V2" "SINCAL_MARCA_DE_V1"))
  (if (tblsearch "BLOCK" name) (progn (princ "\nDefinition already exists") (quit)))
  (if (not (tblsearch "STYLE" "RomanD")) (progn (princ "\nRomanD required") (quit)))
  (entmake (list '(0 . "BLOCK") (cons 2 name) '(70 . 2) '(10 0.0 0.0 0.0)))
  (entmake '((0 . "CIRCLE") (8 . "0") (62 . 1) (10 0.0 0.0 0.0) (40 . 1.25)))
  (SCMB:Attribute "XX" "1" 0.0 T)
  (SCMB:Attribute "CANT_TOTAL" "172" 1.7 nil)
  (SCMB:Attribute "MARCA" "%%c12" 6.0 nil)
  ;; Prefix belongs to the same attribute so flip cannot reverse L= and value.
  (SCMB:Attribute "LARGO" "L=368" 10.0 nil)
  (entmake '((0 . "ENDBLK")))
  (vlax-for obj (vla-item (vla-get-Blocks (SCM:Doc)) name)
    (if (= "AcDbAttributeDefinition" (vla-get-ObjectName obj))
      (progn
        (vla-put-LockPosition obj :vlax-true)
        ;; Manual values stay single-line for direct editing in Ctrl+1.
        (if (= "MARCA" (vla-get-TagString obj))
          (progn
            (vla-put-MTextAttribute obj :vlax-true)
            (vla-UpdateMTextAttribute obj)
            (SCMB:Mask (vlax-vla-object->ename obj)))))))
  (regapp "AcadAnnotative")
  (setq en (vlax-vla-object->ename (vla-item (vla-get-Blocks (SCM:Doc)) name)))
  (entmod (append (entget en)
    '((-3 ("AcadAnnotative" (1000 . "AnnotativeData") (1002 . "{")
          (1070 . 1) (1070 . 1) (1002 . "}"))))))
  (setvar "OSMODE" 0) (setvar "MIRRTEXT" 0) (setvar "FILEDIA" 0)
  (setvar "BACTIONBARMODE" 1)
  (command "_.-BEDIT" name)
  (setq descriptions (ssget "_X" '((0 . "ATTDEF") (2 . "CANT_TOTAL,MARCA,LARGO"))))
  (command "_.BPARAMETER" "_Flip" '(0 -2 0) '(0 3 0) '(-2 -3 0) 1)
  (command "_.BACTION" '(0 2 0) descriptions "")
  (if SCMB:NewPresentation
    (progn (command "_.BPARAMETER" "_Visibility" '(2 3 0) 1)
      (SCMB:States T nil nil)))
  (command "_.BSAVE")
  (command "_.BCLOSE")
  (princ "\nSCMDB_BUILD_COMPLETE")
  (princ))

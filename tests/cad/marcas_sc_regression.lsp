;;; Native tests in a disposable drawing only. No project drawing is saved.
(defun SCMT:Assert (value label)
  (if SCMT:Report (write-line (strcat (if value "PASS: " "FAIL: ") label) SCMT:Report))
  (if value (princ (strcat "\nPASS: " label))
    (progn (setq SCMT:Failures (1+ SCMT:Failures)) (princ (strcat "\nFAIL: " label)))))
(defun SCMT:Run (/ doc space table obj obj2 id resolve en fields mark)
  (setq SCMT:Failures 0 doc (SCM:Doc) space (vla-get-ModelSpace doc))
  (foreach mark '("5" "5a" "5B" "12AB" " 5a ")
    (SCMT:Assert (SCM:ValidMark mark) (strcat "valid mark: " mark)))
  (foreach mark '("" "A" "5 a" "5a2" "5.2" "=5+1" "5\\P" "5%<")
    (SCMT:Assert (not (SCM:ValidMark mark)) (strcat "invalid mark: " mark)))
  (setq table (vla-AddTable space (vlax-3d-point '(0 0 0)) 6 4 3.0 12.0))
  (vla-SetText table 0 0 "ARMADURAS TEST")
  (vla-SetText table 1 0 "MARCA")
  (vla-SetText table 1 1 "#")
  (vla-SetText table 1 2 "%%c")
  (vla-SetText table 1 3 "@")
  (vla-SetText table 2 0 "5")
  (vla-SetText table 2 1 "179")
  (vla-SetText table 2 2 "10")
  (vla-SetText table 2 3 "20")
  (vla-SetText table 3 0 "6")
  (vla-SetText table 3 1 "10")
  (vla-SetText table 3 2 "12")
  (vla-SetText table 3 3 "5")
  (SCMT:Assert (SCM:TableP table) "table schema")
  (SCMT:Assert (= 2 (SCM:RowByMark table "5")) "row lookup")
  (setq obj (vla-InsertBlock space (vlax-3d-point '(30 0 0)) (SCM:BasicDefinition) 1.0 1.0 1.0 0.0))
  (SCMT:Assert (SCM:MarkP obj) "generated block has editable attributes")
  (SCM:Bind obj table 2)
  (SCM:Evaluate (list obj))
  (setq id (SCM:RowID table 2))
  (SCMT:Assert (and id (= (cadr (SCM:Metadata obj)) id)) "persistent cell and block identity")
  (SCMT:Assert (SCM:Healthy obj (SCM:Resolve obj)) "native fields and table references valid")
  (SCMT:Assert (= "5" (vla-get-TextString (cdr (assoc "XX" (SCM:Attrs obj))))) "field evaluated: mark")
  (SCMT:Assert (= "%%c10@20" (vla-get-TextString (cdr (assoc "MARCA" (SCM:Attrs obj))))) "field evaluated: diameter/spacing")
  (vla-SetText table 2 3 "7.500000")
  (SCM:Evaluate (list obj))
  (SCMT:Assert (= "%%c10@7.5" (vla-get-TextString (cdr (assoc "MARCA" (SCM:Attrs obj))))) "spacing shows one decimal without trailing zeros")
  (SCMT:Assert (= "179 %%c10@7.5" (vla-get-TextString (cdr (assoc "MARCA_CANT" (SCM:Attrs obj))))) "quantity stays integer in combined label")
  (SCM:PutText (cdr (assoc "MARCA" (SCM:Attrs obj)))
    (strcat "%%c" (vl-string-subst "" " \\f \"%lu2%pr1%zs8\"" (SCM:Field table 2 "C"))
      "@" (vl-string-subst "" " \\f \"%lu2%pr1%zs8\"" (SCM:Field table 2 "D"))))
  (SCMT:Assert (not (SCM:Healthy obj (SCM:Resolve obj))) "legacy unformatted fields detected")
  (SCM:SyncOne obj)
  (SCM:Evaluate (list obj))
  (SCMT:Assert (and (SCM:Healthy obj (SCM:Resolve obj))
    (= "%%c10@7.5" (vla-get-TextString (cdr (assoc "MARCA" (SCM:Attrs obj)))))) "legacy fields repaired with one decimal")
  (vla-SetText table 2 3 "7.56")
  (SCM:Evaluate (list obj))
  (SCMT:Assert (= "%%c10@7.6" (vla-get-TextString (cdr (assoc "MARCA" (SCM:Attrs obj))))) "spacing rounds to one decimal")
  (SCMT:Assert (equal 7.56 (distof (vla-GetText table 2 3) 2) 1.0e-8) "display rounding does not change table value")
  (vla-SetText table 2 3 "20")
  (vla-SetText table 2 2 "16")
  (SCM:Evaluate (list obj))
  (SCMT:Assert (= "%%c16@20" (vla-get-TextString (cdr (assoc "MARCA" (SCM:Attrs obj))))) "table edit refreshes label")
  (vla-SetText table 2 0 "15")
  (SCMT:Assert (= 2 (cadr (SCM:Resolve obj))) "renumbering retains identity")
  (vla-InsertRows table 2 3.0 1)
  (setq resolve (SCM:Resolve obj))
  (SCMT:Assert (and (listp resolve) (= 3 (cadr resolve))) "inserted row preserves and moves ID")
  (SCM:Bind obj (car resolve) (cadr resolve))
  (SCM:Evaluate (list obj))
  (SCMT:Assert (= "15" (vla-get-TextString (cdr (assoc "XX" (SCM:Attrs obj))))) "repair after renumber and row insertion")
  (vla-SetText table 3 0 "5a")
  (SCMT:Assert (= 3 (cadr (SCM:Resolve obj))) "alphanumeric rename retains row identity")
  (SCMT:Assert (= 3 (SCM:RowByMark table " 5A ")) "case-insensitive alphanumeric lookup")
  (SCM:Bind obj table 3)
  (SCM:Evaluate (list obj))
  (SCMT:Assert (= "5a" (vla-get-TextString (cdr (assoc "XX" (SCM:Attrs obj))))) "mark spelling preserved")
  (SCMT:Assert (= "%%c16@20" (vla-get-TextString (cdr (assoc "MARCA" (SCM:Attrs obj))))) "alphanumeric mark keeps numeric fields valid")
  (vla-SetText table 2 0 "5b")
  (vla-SetText table 2 1 "8")
  (vla-SetText table 2 2 "12")
  (vla-SetText table 2 3 "15")
  (SCM:PutText (cdr (assoc "XX" (SCM:Attrs obj))) "5B")
  (SCM:SyncOne obj)
  (SCM:Evaluate (list obj))
  (SCMT:Assert (and (= 2 (cadr (SCM:Resolve obj)))
    (= "5b" (vla-get-TextString (cdr (assoc "XX" (SCM:Attrs obj)))))
    (= "%%c12@15" (vla-get-TextString (cdr (assoc "MARCA" (SCM:Attrs obj)))))) "editing XX links to inserted alphanumeric row")
  (SCM:Bind obj table 3)
  (vla-SetText table 4 0 "5A")
  (SCMT:Assert (= 'STR (type (SCM:Resolve obj))) "mixed-case duplicate rejected")
  (SCM:SyncOne obj)
  (SCMT:Assert (= "[SIN VINCULO]" (vla-get-TextString (cdr (assoc "MARCA" (SCM:Attrs obj))))) "ambiguous alphanumeric mark clears stale description")
  (vla-SetText table 4 0 "6")
  (SCM:SyncOne obj)
  (SCMT:Assert (SCM:Healthy obj (SCM:Resolve obj)) "removing duplicate repairs binding")
  (vla-SetText table 3 0 "5+1")
  (SCMT:Assert (= 'STR (type (SCM:Resolve obj))) "formula-like mark remains rejected")
  (vla-SetText table 3 0 "15")
  (vla-SetText table 4 0 "15")
  (SCMT:Assert (= 'STR (type (SCM:Resolve obj))) "duplicate visible mark detected")
  (vla-SetText table 4 0 "6")
  (vla-SetText table 3 2 "VAR")
  (SCMT:Assert (= 'STR (type (SCM:Resolve obj))) "invalid diameter detected")
  (vla-SetText table 3 2 "16")
  (setq obj2 (vla-Copy obj))
  (SCM:Bind obj2 table 4)
  (SCM:Evaluate (list obj2))
  (SCMT:Assert (/= (cadr (SCM:Metadata obj)) (cadr (SCM:Metadata obj2))) "reassign updates metadata")
  (SCMT:Assert (= "6" (vla-get-TextString (cdr (assoc "XX" (SCM:Attrs obj2))))) "reassign updates displayed mark")
  (vla-put-TextString (cdr (assoc "MARCA" (SCM:Attrs obj2))) "MANUAL")
  (SCMT:Assert (not (SCM:Healthy obj2 (SCM:Resolve obj2))) "manual override detected")
  (vla-SetCustomData table 5 0 "SINCAL_MARCA_ID_V1" (vlax-make-variant id vlax-vbString))
  (SCMT:Assert (= 'STR (type (SCM:Resolve obj))) "duplicated ID rejected")
  (vla-DeleteRows table 5 1)
  (vla-DeleteRows table 3 1)
  (SCMT:Assert (= 'STR (type (SCM:Resolve obj))) "deleted row rejected without guessing")
  (vla-Delete table)
  (SCMT:Assert (= 'STR (type (SCM:Resolve obj2))) "missing table detected")
  (princ (strcat "\nMARCAS_SC_TEST_FAILURES=" (itoa SCMT:Failures) "\n")))
(SCMT:Run)
(princ)

;;; Only in disposable native CAD drawings through test_of2_native.py.
(vl-load-com)
(defun OF2T:Assert (ok label / stream)
  (if (not ok) (setq OF2T:failures (1+ OF2T:failures)))
  (setq stream (open OF2T:report "a"))
  (write-line (strcat (if ok "PASS " "FAIL ") label) stream)
  (close stream))
(defun OF2T:Point (obj property)
  (vlax-safearray->list (vlax-variant-value (vlax-get-property obj property))))
(defun OF2T:Prepare (report / obj result objects radii before coords pl)
  (setq OF2T:oldMode (getenv "SINCAL_OF2_MODO") OF2T:hasModeSnapshot T)
  (setenv "SINCAL_OF2_MODO" "")
  (setq OF2T:report report OF2T:failures 0
        OF2T:doc (vla-get-ActiveDocument (vlax-get-acad-object))
        OF2T:space (vla-get-ModelSpace OF2T:doc))
  (setvar "TILEMODE" 1)
  (setq obj (vla-AddLine OF2T:space (vlax-3d-point '(0 0 0)) (vlax-3d-point '(10 0 0))))
  (vla-put-Color obj 3)
  (setq result (OF2:Pair obj 2.0) objects (cadr result))
  (OF2T:Assert (and (car result) (= 2 (length objects))) "line: two offsets")
  (OF2T:Assert (equal '(-2.0 2.0)
    (vl-sort (mapcar '(lambda (o) (cadr (OF2T:Point o 'StartPoint))) objects) '<) 1e-8)
    "line: opposite sides at exact distance")
  (OF2T:Assert (and (= 3 (vla-get-Color (car objects)))
                    (= 3 (vla-get-Color (cadr objects)))) "source color retained")
  (OF2T:Assert (equal '(0.0 0.0 0.0) (OF2T:Point obj 'StartPoint) 1e-8) "original unchanged")
  (setq obj (vla-AddCircle OF2T:space (vlax-3d-point '(30 0 0)) 10.0)
        result (OF2:Pair obj 2.0))
  (OF2T:Assert (and (car result)
    (equal '(8.0 12.0) (vl-sort (mapcar 'vla-get-Radius (cadr result)) '<) 1e-8))
    "circle: inner and outer radii")
  (setq before (vla-get-Count OF2T:space) result (OF2:Pair obj 15.0))
  (OF2T:Assert (not (car result)) "impossible inner circle rejected")
  (OF2T:Assert (= before (vla-get-Count OF2T:space)) "failed second side removes first offset")
  (OF2T:Assert (equal 10.0 (vla-get-Radius obj) 1e-8) "failed operation preserves original")
  (setq coords (vlax-make-safearray vlax-vbDouble '(0 . 5)))
  (vlax-safearray-fill coords '(0.0 30.0 10.0 30.0 10.0 40.0))
  (setq pl (vla-AddLightWeightPolyline OF2T:space coords)
        result (OF2:Pair pl 1.0))
  (OF2T:Assert (and (car result) (= 2 (length (cadr result)))) "bent polyline: two offsets")
  (OF2T:Assert (equal '(0.0 30.0 10.0 30.0 10.0 40.0)
    (OF2T:Point pl 'Coordinates) 1e-8) "polyline original unchanged")
  ;; Actual command uses preselection, not the internal geometry helper.
  (setq OF2T:line (vla-AddLine OF2T:space (vlax-3d-point '(50 50 0))
                     (vlax-3d-point '(60 50 0)))
        OF2T:before (vla-get-Count OF2T:space)
        OF2:last nil)
  (sssetfirst nil (ssadd (vlax-vla-object->ename OF2T:line)))
  (princ))
(defun OF2T:Select ()
  (sssetfirst nil (ssadd (vlax-vla-object->ename OF2T:line)))
  (princ))
(defun OF2T:CheckUndo (offset mode)
  (OF2T:Assert (equal offset OF2:last 1e-8) "physical distance per side remembered")
  (OF2T:Assert (= mode (getenv "SINCAL_OF2_MODO")) "mode saved for next invocation")
  (OF2T:Assert (= OF2T:before (vla-get-Count OF2T:space)) "single UNDO removes both offsets")
  (OF2T:Assert (not (vlax-erased-p OF2T:line)) "UNDO retains original")
  (princ))
(defun OF2T:RestoreMode ()
  (if OF2T:hasModeSnapshot
    (progn
      (setenv "SINCAL_OF2_MODO" (if OF2T:oldMode OF2T:oldMode ""))
      (setq OF2T:hasModeSnapshot nil)))
  (princ))
(defun OF2T:Finish (/ stream)
  (OF2T:RestoreMode)
  (setq stream (open OF2T:report "a"))
  (write-line (strcat "DONE failures=" (itoa OF2T:failures)) stream)
  (close stream)
  (princ))

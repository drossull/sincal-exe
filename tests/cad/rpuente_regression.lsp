;;; Run only in a disposable drawing. Exercises the real CAD curve API.
(defun RPT:Assert (test label)
  (setq RPT:Checks (1+ RPT:Checks))
  (if test (princ (strcat "\nPASS: " label))
    (progn (setq RPT:Failures (1+ RPT:Failures)) (princ (strcat "\nFAIL: " label)))))
(defun RPT:Near (a b) (and (numberp a) (equal a b 1.0e-6)))
(defun RPT:Radius (result) (cdr (assoc 'radio result)))
(defun RPT:Run (/ r ent poly vertices old e last-before beforedata result markers old-pdmode old-pdsize)
  (setq RPT:Checks 0 RPT:Failures 0)
  (setq r (RP:Three '(1.0 0.0 0.0) '(0.0 1.0 0.0) '(-1.0 0.0 0.0)))
  (RPT:Assert (RPT:Near (RPT:Radius r) 1.0) "three point unit circle")
  (RPT:Assert (equal (cdr (assoc 'centro r)) '(0.0 0.0 0.0) 1.0e-8) "three point center")
  (setq r (RP:Three '(501000.0 6300000.0 30.0) '(500000.0 6301000.0 12.0) '(499000.0 6300000.0 0.0)))
  (RPT:Assert (RPT:Near (RPT:Radius r) 1000.0) "UTM stability and XY projection")
  (RPT:Assert (assoc 'error (RP:Three '(0.0 0.0) '(1.0 0.0) '(2.0 0.0))) "collinear rejected")
  (RPT:Assert (assoc 'error (RP:Three '(1.0 1.0) '(1.0 1.0) '(2.0 3.0))) "duplicate points rejected")
  (RPT:Assert (assoc 'error (RP:Three '(0.0 0.0) '(1.0 1.0e-12) '(2.0 0.0))) "near collinear rejected")
  (RPT:Assert (assoc 'aviso (RP:Three '(0.0 0.0) '(1.0 0.0001) '(2.0 0.0))) "shallow arc warning")
  (RPT:Assert (RPT:Near (RPT:Radius (RP:Bulge '(0.0 0.0) '(20.0 0.0) 1.0)) 10.0) "semicircle")
  (RPT:Assert (RPT:Near (RPT:Radius (RP:Bulge '(0.0 0.0) '(20.0 0.0) -0.5)) 12.5) "negative bulge")
  (RPT:Assert (RPT:Near (RPT:Radius (RP:Bulge '(0.0 0.0) '(20.0 0.0) 2.0)) 12.5) "major arc")
  (RPT:Assert (assoc 'error (RP:Bulge '(0.0 0.0) '(20.0 0.0) 0.0)) "straight segment rejected")
  (entmake '((0 . "CIRCLE") (10 5.0 6.0 0.0) (40 . 150.0)))
  (setq ent (entlast) beforedata (entget ent) last-before (entlast))
  (RPT:Assert (RPT:Near (RPT:Radius (RP:Measure ent '(5.0 156.0 0.0))) 150.0) "circle entity")
  (RPT:Assert (and (equal beforedata (entget ent)) (eq last-before (entlast))) "measurement does not mutate drawing")
  (entmake '((0 . "ARC") (10 0.0 0.0 0.0) (40 . 250.0) (50 . 0.0) (51 . 1.0)))
  (RPT:Assert (RPT:Near (RPT:Radius (RP:Measure (entlast) '(250.0 0.0 0.0))) 250.0) "arc entity")
  (entmake '((0 . "CIRCLE") (10 0.0 0.0 0.0) (40 . 5.0) (210 0.0 1.0 0.0)))
  (RPT:Assert (assoc 'error (RP:Measure (entlast) '(0.0 0.0 0.0))) "tilted circle rejected")
  (entmake '((0 . "CIRCLE") (10 1.0 2.0 0.0) (40 . 5.0) (210 0.0 0.0 -1.0)))
  (setq r (RP:Measure (entlast) '(0.0 0.0 0.0)))
  (RPT:Assert (equal (cdr (assoc 'centro r)) '(-1.0 2.0 0.0) 1.0e-8) "negative normal center in WCS")
  (entmake '((0 . "LWPOLYLINE") (100 . "AcDbEntity") (100 . "AcDbPolyline")
    (90 . 4) (70 . 0) (10 0.0 0.0) (42 . 1.0) (10 20.0 0.0) (42 . 0.5)
    (10 40.0 0.0) (42 . 0.0) (10 60.0 0.0) (42 . 1.0)))
  (setq poly (entlast) vertices (RP:Vertices poly))
  (RPT:Assert (= (length vertices) 4) "polyline vertices decoded")
  (RPT:Assert (RPT:Near (RPT:Radius (RP:Measure poly '(10.0 -9.0 0.0))) 10.0) "clicked first curved segment")
  (RPT:Assert (RPT:Near (RPT:Radius (RP:Measure poly '(30.0 -5.0 0.0))) 12.5) "clicked second radius")
  (RPT:Assert (assoc 'error (RP:Measure poly '(50.0 0.0 0.0))) "clicked straight segment")
  (RPT:Assert (assoc 'error (RP:Segment vertices nil 1.0)) "ambiguous interior vertex")
  (RPT:Assert (RPT:Near (RPT:Radius (RP:Segment vertices nil 0.0)) 10.0) "open start vertex")
  (RPT:Assert (assoc 'error (RP:Segment vertices nil 3.0)) "open endpoint chooses last straight segment")
  (RPT:Assert (RPT:Near (RPT:Radius (RP:Segment vertices T 3.5)) 30.0) "closed final segment")
  (RPT:Assert (assoc 'error (RP:Segment vertices T 0.0)) "closed join vertex ambiguous")
  (entmake '((0 . "POLYLINE") (66 . 1) (10 0.0 0.0 0.0) (70 . 0)))
  (setq old (entlast))
  (entmake '((0 . "VERTEX") (10 0.0 0.0 0.0) (42 . 1.0)))
  (entmake '((0 . "VERTEX") (10 20.0 0.0 0.0)))
  (entmake '((0 . "SEQEND")))
  (RPT:Assert (RPT:Near (RPT:Radius (RP:Measure old '(10.0 -10.0 0.0))) 10.0) "legacy 2D polyline")
  (RPT:Assert (RPT:Near (RP:Metres 5380.0 "Centimetros") 53.8) "centimeters conversion")
  (RPT:Assert (RPT:Near (RP:Metres 1000.0 "Milimetros") 1.0) "millimeters conversion")
  (RPT:Assert (null (RP:Metres 50.0 "Dibujo")) "unitless not guessed")
  (setq old-pdmode (getvar "PDMODE") old-pdsize (getvar "PDSIZE")
        markers (RP:MarkCenter '(500000.0 6300000.0 12.0) 362132.0))
  (RPT:Assert (= 3 (length markers)) "point and two cross lines created")
  (RPT:Assert (equal (cdr (assoc 10 (entget (car markers)))) '(500000.0 6300000.0 12.0) 1.0e-8) "center stays in drawing units and WCS")
  (RPT:Assert (= "POINT" (cdr (assoc 0 (entget (car markers))))) "center supports node snap")
  (RPT:Assert (and (= old-pdmode (getvar "PDMODE")) (= old-pdsize (getvar "PDSIZE"))) "point display settings unchanged")
  (RPT:Assert (equal (mapcar '(lambda (a b) (/ (+ a b) 2.0))
    (cdr (assoc 10 (entget (cadr markers)))) (cdr (assoc 11 (entget (cadr markers)))))
    '(500000.0 6300000.0 12.0) 1.0e-8) "cross centered exactly")
  (princ (strcat "\nRPUENTE_CHECKS=" (itoa RPT:Checks)
    "\nRPUENTE_FAILURES=" (itoa RPT:Failures) "\n"))
  (princ)
)
(RPT:Run)

;;; Run in a disposable drawing after loading lisps/TXT-JOIN.lsp.
;;; Tests exercise native TEXT metrics and MTEXT creation, not a Python port.
(defun TXUT:Assert (value label)
  (if value
    (princ (strcat "\nPASS: " label))
    (progn (setq TXUT:Failures (1+ TXUT:Failures))
      (princ (strcat "\nFAIL: " label))))
)

(defun TXUT:Text (s x y h a / ent)
  (entmake (list '(0 . "TEXT") '(8 . "0") (cons 10 (TXU:Rotate (list x y 0.0) a))
    (cons 40 h) (cons 1 s) (cons 50 a) '(7 . "Standard")))
  (entlast)
)

(defun TXUT:Record (s x y)
  (TXU:Read (TXUT:Text s x y 1.0 0.0) 0.0)
)

(defun TXUT:Content (e / out pair)
  (setq out "")
  (foreach pair (entget e)
    (if (member (car pair) '(1 3)) (setq out (strcat out (cdr pair)))))
  out
)

(defun TXUT:Run (/ a b c d rows content ref mt ss col long i r rotated merged justified)
  (setq TXUT:Failures 0)
  (setvar "CMDECHO" 0)
  (setvar "OSMODE" 0)
  (TXUT:Assert (= "\\U+2205 \\U+00B0 \\U+00B1" (TXU:Escape "%%c %%d %%p")) "engineering symbols")
  (TXUT:Assert (= "\\Ltitulo\\l" (TXU:Escape "%%utitulo")) "underline closed")
  (TXUT:Assert (= "\\{A\\}\\\\P" (TXU:Escape "{A}\\P")) "literal braces and slash")
  (TXUT:Assert (= "\\U+00F1" (TXU:Escape "\\U+00F1")) "unicode sequence preserved")
  (TXUT:Assert (= "%" (TXU:Escape "%%%")) "literal percent")
  (TXUT:Assert (= "A" (TXU:Escape "%%065")) "numeric character code")
  (setq a (TXUT:Record "HOR" 0.0 20.0)
        b (TXUT:Record "MIGON" (+ (nth 3 a) 0.1) 20.05)
        c (TXUT:Record "EN VIGA" (+ (nth 3 b) 0.7) 20.0)
        d (TXUT:Record "SEGUNDA LINEA" 0.0 18.5)
        rows (TXU:Rows (list d c b a) 0.35))
  (TXUT:Assert (= 2 (length rows)) "jitter and scrambled selection grouped")
  (TXUT:Assert (equal (mapcar 'cadr (car rows)) '("HOR" "MIGON" "EN VIGA")) "left to right")
  (TXUT:Assert (= "SEGUNDA LINEA" (cadr (car (cadr rows)))) "top to bottom")
  (setq merged (TXU:JoinRow (car rows) 0.35 1.0 0.0))
  (TXUT:Assert (not (vl-string-search "} {" (substr merged 1 (vl-string-search "MIGON" merged))))
    "no inferred space within word")
  ;; Font side bearings can turn this gap into one or several spaces.
  (TXUT:Assert (or (vl-string-search "} {" merged)
                  (vl-string-search "}\\~\\~" merged)) "inferred word boundary")
  (setq r (TXUT:Record "0" 0.0 0.0))
  (TXUT:Assert (= 2 (length (car (TXU:Rows (list r r) 0.35)))) "no loss of duplicate characters")
  (setq a (TXUT:Record "TITULO" 0.0 30.0)
        b (TXUT:Record "ITEM" 0.0 25.0)
        rows (TXU:Rows (list b a) 0.35))
  (TXUT:Assert (vl-string-search "\\P\\P" (TXU:Build rows 0.35 1.0 0.0)) "section blank line")
  (setq a (TXUT:Record "NUMERO" 0.0 0.0)
        b (TXUT:Record "450" 20.0 0.0))
  (TXUT:Assert (vl-string-search "\\~\\~" (TXU:JoinRow (list a b) 0.35 1.0 0.0)) "table separation")
  ;; Rotation independent of current UCS.
  (setq rotated (/ pi 3.0)
        a (TXU:Read (TXUT:Text "ARRIBA" 10.0 20.0 1.0 rotated) rotated)
        b (TXU:Read (TXUT:Text "ABAJO" 10.0 18.5 1.0 rotated) rotated))
  (TXUT:Assert (equal (nth 4 a) 20.0 1.0e-8) "rotated baseline")
  (TXUT:Assert (= "ARRIBA" (cadr (car (car (TXU:Rows (list b a) 0.35))))) "rotated reading order")
  ;; Unsupported geometry is counted and remains in the drawing.
  (setq ref (entget (car a)) ss (ssadd))
  (ssadd (car a) ss) (ssadd (car b) ss)
  (ssadd (TXUT:Text "OTRO ANGULO" 0.0 0.0 1.0 0.0) ss)
  (entmake '((0 . "LINE") (8 . "0") (10 0.0 0.0 0.0) (11 1.0 1.0 0.0)))
  (ssadd (entlast) ss)
  (setq col (TXU:Collect ss ref))
  (TXUT:Assert (and (= 2 (length (car col))) (= 2 (cadr col))) "incompatible entities excluded")
  (TXUT:Assert (entget (ssname ss 3)) "geometry preserved")
  ;; Right justified TEXT gets a computed group 10 baseline.
  (entmake '((0 . "TEXT") (8 . "0") (10 0.0 0.0 0.0) (11 30.0 10.0 0.0)
    (40 . 1.0) (1 . "RIGHT") (7 . "Standard") (72 . 2) (73 . 0)))
  (entupd (entlast))
  (setq justified (TXU:Read (entlast) 0.0))
  (TXUT:Assert (and (< (nth 2 justified) 30.0) (equal (nth 3 justified) 30.0 0.15)
    (equal (nth 4 justified) 10.0 1.0e-6)) "right justification extents")
  ;; Native MTEXT stores strings exceeding the DXF group 1 limit without loss.
  (setq long "" i 0)
  (repeat 120 (setq long (strcat long "{\\H1x;LINEA " (itoa i) " %%c}\\P") i (1+ i)))
  (setq mt (TXU:Create ref '(100.0 100.0 0.0) long 1.0))
  (TXUT:Assert (and mt (= "MTEXT" (cdr (assoc 0 (entget mt))))) "native MTEXT created")
  (TXUT:Assert (= long (TXUT:Content mt)) "long text roundtrip")
  (TXUT:Assert (equal (cdr (assoc 11 (entget mt)))
    (list (cos rotated) (sin rotated) 0.0) 1.0e-6) "MTEXT orientation")
  (TXUT:Assert (assoc 330 (entget mt)) "MTEXT owned by drawing space")
  (TXUT:Assert (entget (car a)) "creation preserves originals")
  (princ (strcat "\nTXT-JOIN_TEST_FAILURES=" (itoa TXUT:Failures) "\n"))
  (princ)
)
(TXUT:Run)

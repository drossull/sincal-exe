;;; Disposable native migration test. No original drawings opened or saved.
(setq sp (vla-get-ModelSpace (SCM:Doc)) tab (vla-AddTable sp (vlax-3d-point '(0 80 0)) 3 4 3.0 12.0)
      SCMT:Old nil SCMT:New nil)
(foreach item '((0 0 "UPGRADE") (1 0 "MARCA") (1 1 "#") (1 2 "%%c") (1 3 "@") (2 0 "7a") (2 1 "163") (2 2 "12") (2 3 "7.5"))
  (vla-SetText tab (car item) (cadr item) (caddr item)))
(foreach name '("SINCAL_MARCA_SC_V2" "SINCAL_MARCA_DE_V1")
  (if (= name "SINCAL_MARCA_DE_V1") (progn (setvar "TILEMODE" 0) (vla-put-MSpace (SCM:Doc) :vlax-false)))
  (setq obj (vla-InsertBlock (if (= name "SINCAL_MARCA_DE_V1") (vla-get-PaperSpace (SCM:Doc)) sp)
    (vlax-3d-point '(22 33 0)) (SCM:DefinitionNamed name) 2.5 2.5 2.5 0.42))
  (SCM:Bind obj tab 2)
  (foreach p (vlax-invoke obj 'GetDynamicBlockProperties)
    (if (wcmatch (strcase (vla-get-PropertyName p)) "*FLIP*") (vla-put-Value p (vlax-make-variant 1 vlax-vbInteger))))
  (if (SCM:DetailP obj)
    (progn (SCM:PutText (cdr (assoc "CANT_TOTAL" (SCM:Attrs obj))) "207")
           (SCM:PutText (cdr (assoc "LARGO" (SCM:Attrs obj))) "L=432.1"))
    (foreach p (vlax-invoke obj 'GetDynamicBlockProperties)
      (if (= 'STR (type (vlax-get p 'Value))) (vla-put-Value p (vlax-make-variant "CON_CANTIDAD" vlax-vbString)))))
  (if (= name "SINCAL_MARCA_SC_V2")
    (vl-cmdf "_.-OBJECTSCALE" (ssadd (vlax-vla-object->ename obj)) "" "_Add" "1:2" ""))
  (SCMT:Assert (not (SCM:UpIssue obj)) "old master passes preflight")
  (setq SCMT:Old (cons (list (vlax-vla-object->ename obj) (SCM:UpScales obj) (SCM:UpDynamics obj)) SCMT:Old)))
(setq SCMT:Locked (vla-Copy obj) SCMT:Layer (vla-Add (vla-get-Layers (SCM:Doc)) "SCMT_LOCKED"))
(vla-put-Layer SCMT:Locked "SCMT_LOCKED")
(vla-put-Lock SCMT:Layer :vlax-true)
(SCMT:Assert (SCM:UpIssue SCMT:Locked) "locked reference rejected before changes")
(setvar "TILEMODE" 1)
(defun SCMT:CheckUp (/ obj row pair)
  (SCMT:Assert (= "Model" (getvar "CTAB")) "original layout restored")
  (setq SCMT:New nil)
  (foreach obj (SCM:Managed)
    (if (and (member (SCM:UpName obj) '("SINCAL_MARCA_SC_V3" "SINCAL_MARCA_DE_V2"))
             (equal (car (SCM:Metadata obj)) (vla-get-Handle tab)))
      (setq SCMT:New (cons obj SCMT:New))))
  (SCMT:Assert (= 2 (length SCMT:New)) "public command migrates exactly both old marks")
  (foreach obj SCMT:New
    (SCMT:Assert (not (SCM:UpTarget obj)) "current master is not migrated twice")
    (SCMT:Assert (SCM:Healthy obj (SCM:Resolve obj)) "replacement link healthy")
    (SCMT:Assert (equal (vlax-get obj 'InsertionPoint) '(22.0 33.0 0.0) 1e-8) "insertion preserved")
    (SCMT:Assert (equal (vla-get-Rotation obj) 0.42 1e-8) "rotation preserved")
    (SCMT:Assert (equal (vla-get-XScaleFactor obj) (if (and SCMT:Metric (not (SCM:DetailP obj))) 0.0625 2.5) 1e-8) "scale preserved")
    (SCMT:Assert (= (if (SCM:DetailP obj) 1 2) (length (SCM:UpScales obj))) "annotation scales preserved")
    (if (SCM:DetailP obj)
      (progn (SCMT:Assert (/= "Model" (cdr (assoc 410 (entget (vlax-vla-object->ename obj))))) "inactive layout preserved")
             (SCMT:Assert (= "207" (vla-get-TextString (cdr (assoc "CANT_TOTAL" (SCM:Attrs obj))))) "manual total preserved")
             (SCMT:Assert (= "L=432.1" (vla-get-TextString (cdr (assoc "LARGO" (SCM:Attrs obj))))) "manual length preserved")))
    (foreach pair (SCM:UpDynamics obj)
      (if (wcmatch (strcase (car pair)) "*FLIP*") (SCMT:Assert (= 1 (cdr pair)) "flip preserved"))))
  (SCMT:Assert (= "SINCAL_MARCA_DE_V1" (SCM:UpName SCMT:Locked)) "locked block unchanged")
  (foreach row SCMT:Old (SCMT:Assert (not (entget (car row))) "old reference replaced after verification")))
(defun SCMT:CheckUndo (/ row)
  (foreach row SCMT:Old
    (SCMT:Assert (entget (car row)) "UNDO restores original reference")
    (SCMT:Assert (equal (cadr row) (SCM:UpScales (vlax-ename->vla-object (car row)))) "UNDO restores scales")))
(defun SCMT:ForceFailure ()
  (setq SCMT:CountBefore (sslength (ssget "_X" '((0 . "INSERT")))))
  (defun SCM:UpSetDynamics (obj values) (SCM:Fail "SCMT: fallo intencional despues de insertar.")))
(defun SCMT:CheckRollback ()
  (SCMT:Assert (= SCMT:CountBefore (sslength (ssget "_X" '((0 . "INSERT"))))) "failure rolls back inserted replacement")
  (SCMT:Assert (= "Model" (getvar "CTAB")) "failure restores original layout"))

(setq sp (vla-get-ModelSpace (SCM:Doc)) tab (vla-AddTable sp (vlax-3d-point '(0 40 0)) 3 4 3.0 12.0))
(foreach item '((0 0 "TEST") (1 0 "MARCA") (1 1 "#") (1 2 "%%c") (1 3 "@") (2 0 "5a") (2 1 "163") (2 2 "8") (2 3 "20"))
  (vla-SetText tab (car item) (cadr item) (caddr item)))
(foreach kind '(nil T)
  (setq obj (vla-InsertBlock sp (vlax-3d-point '(0 -20 0))
    (SCM:DefinitionNamed (if kind "SINCAL_MARCA_DE_V2" "SINCAL_MARCA_SC_V3")) 2.5 2.5 2.5 0.0))
  (if kind
    (progn (SCM:PutText (cdr (assoc "CANT_TOTAL" (SCM:Attrs obj))) "172")
      (SCM:PutText (cdr (assoc "LARGO" (SCM:Attrs obj))) "L=368")))
  (SCM:Bind obj tab 2)
  (setq vis nil flip nil)
  (foreach p (vlax-invoke obj 'GetDynamicBlockProperties)
    (if (= 'STR (type (vlax-get p 'Value))) (setq vis p))
    (if (wcmatch (strcase (vla-get-PropertyName p)) "*FLIP*") (setq flip p)))
  (SCMT:Assert (= (if kind 6 12) (length (vlax-get vis 'AllowedValues))) "all combined visibility states")
  (foreach state (vlax-get vis 'AllowedValues)
    (vla-put-Value vis (vlax-make-variant state vlax-vbString))
    (SCM:SyncOne obj)
    (SCM:Evaluate (list obj))
    (setq options (SCM:Presentation obj) attrs (SCM:Attrs obj))
    (SCMT:Assert (SCM:Healthy obj (SCM:Resolve obj)) (strcat "healthy state " state))
    (if kind
      (progn
        (SCMT:Assert (= (vla-get-TextString (cdr (assoc "CANT_TOTAL" attrs))) (strcat (car options) "172")) "manual quantity preserved")
        (SCMT:Assert (= (vla-get-TextString (cdr (assoc "LARGO" attrs))) (strcat "L=368" (cadr options))) "manual length preserved"))
      (SCMT:Assert (= (vla-get-TextString (cdr (assoc "MARCA_CANT" attrs))) (strcat (car options) "163 %%c8@20" (cadr options))) "linked decorated description"))
    (vla-put-Value flip (vlax-make-variant 1 vlax-vbInteger))
    (SCM:SyncOne obj)
    (SCMT:Assert (SCM:Healthy obj (SCM:Resolve obj)) "flip retains presentation")
    (vla-put-Value flip (vlax-make-variant 0 vlax-vbInteger))))
(SCM:Watch)
(defun c:SCMP-VIS ()
  (vla-put-Value vis (vlax-make-variant "NORMAL" vlax-vbString)) (princ))
(defun c:SCMP-MANUAL ()
  (SCM:PutText (cdr (assoc "CANT_TOTAL" (SCM:Attrs obj))) "200")
  (SCM:PutText (cdr (assoc "LARGO" (SCM:Attrs obj))) "L=450")
  (vla-put-Value vis (vlax-make-variant "SUP_SUPLE" vlax-vbString)) (princ))
(princ)

;;; Native regression on a scratch master. Output stream SNY:report supplied by runner.
(vl-load-com)
(defun SNY:Assert (condition message)
  (setq SNY:checks (1+ SNY:checks))
  (if (not condition)
    (progn (setq SNY:fail (1+ SNY:fail)) (write-line (strcat "FAIL " message) SNY:report))))
(defun SNY:Prop (ref name / found p)
  (foreach p (vlax-invoke ref 'GetDynamicBlockProperties)
    (if (= name (vla-get-PropertyName p)) (setq found p))) found)
(defun SNY:Set (ref name value / prop)
  (setq prop (SNY:Prop ref name))
  (vla-put-Value prop (vlax-make-variant value (vlax-variant-type (vla-get-Value prop)))))
(defun SNY:Attr (ref tag / found a)
  (foreach a (vlax-invoke ref 'GetAttributes)
    (if (= tag (vla-get-TagString a)) (setq found a))) found)
(defun SNY:Geometry (ref / obj tip baseline)
  ;; Inspect world geometry in this disposable test. ZWCAD's anonymous block
  ;; coordinates and annotative scale differ from AutoCAD's internal storage.
  (foreach obj (vlax-invoke ref 'Explode)
    (cond
      ((= "AcDbLine" (vla-get-ObjectName obj))
       (setq tip (vlax-get obj 'EndPoint)))
      ((and (= "AcDbPolyline" (vla-get-ObjectName obj)) (= 1 (vla-get-Color obj)))
       (setq baseline (vlax-get obj 'Coordinates))))
    (vla-Delete obj))
  (list tip baseline))
(defun SNY:Test (/ name scale ref x sign y label geo tip baseline flip expected)
  (setq SNY:fail 0 SNY:checks 0 SNY:doc (vla-get-ActiveDocument (vlax-get-acad-object)))
  (foreach scale '("1:1" "1:100")
    (setvar "CANNOSCALE" scale)
    (foreach name '("NIVEL" "NIVEL_MM")
      (setq ref (vla-InsertBlock (vla-get-ModelSpace SNY:doc) (vlax-3d-point '(0 0 0)) name 1 1 1 0)
            label (strcat name " " scale))
      (vla-put-TextString (SNY:Attr ref "BASE") "100")
      (foreach x '(0.0 30.0 -40.0 1000.0)
        (SNY:Set ref "BASE A NIVEL X" x)
        (foreach sign '(1.0 -1.0 0.0)
          (setq y (* sign (if (= name "NIVEL_MM") 20123.0 20.123))
                expected (cond ((= sign 1.0) "120,123") ((= sign -1.0) "79,877") (T "100,000")))
          (SNY:Set ref "BASE A NIVEL Y" y)
          (foreach flip '((0 0) (0 1) (1 0) (1 1))
            (SNY:Set ref "DER/IZQ" (car flip))
            (SNY:Set ref "ARRIBA/ABAJO" (cadr flip))
            (command "_.UPDATEFIELD" (vlax-vla-object->ename ref) "")
            (vla-Regen SNY:doc 1)
            (setq geo (SNY:Geometry ref) tip (car geo) baseline (cadr geo))
            (SNY:Assert (and tip (equal 0.0 (car tip) 1e-6) (equal y (cadr tip) 1e-5))
              (strcat label " arrow stays on insertion X with signed Y"))
            (SNY:Assert (and baseline (equal 0.0 (+ (car baseline) (caddr baseline)) 1e-6)
                            (equal y (cadr baseline) 1e-5) (equal y (cadddr baseline) 1e-5))
              (strcat label " whole baseline follows arrow"))
            (SNY:Assert (= expected (vla-get-TextString (SNY:Attr ref "NIVEL")))
              (strcat label " editable BASE and signed field remain valid")))))
      (SNY:Set ref "DIST. LINEA" 25.0)
      (command "_.UPDATEFIELD" (vlax-vla-object->ename ref) "")
      (SNY:Assert (= "100,000" (vla-get-TextString (SNY:Attr ref "NIVEL")))
        (strcat label " line length independent of level"))
      (vla-Delete ref)))
  (write-line (strcat "DONE checks=" (itoa SNY:checks) " failures=" (itoa SNY:fail)) SNY:report)
  (close SNY:report) (setq SNY:report nil) (princ))

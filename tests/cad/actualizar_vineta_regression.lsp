;;; Load ACTUALIZAR-VINETA.lsp, then this file; call (SRFT:PatchCases).
;;; Pure DXF-list regression: does not select, modify or save any drawing.
(defun SRFT:Assert (condition message)
  (if (not condition) (progn (princ (strcat "\nFAIL: " message)) (exit))))
(defun SRFT:Options (data)
  (mapcar 'cdr (vl-remove-if-not '(lambda (pair) (= 91 (car pair))) data)))
(defun SRFT:PatchCases (/ source patched enabled)
  (setq source '((0 . "FIELD") (1 . "AcVar")
                 (2 . "\\AcVar CustomDP.Revision") (3 . " \\f \"%tc1\"")
                 (91 . 0)
                 (6 . "ACAD_ROUNDTRIP_2008_FIELD_EVALOPTION") (91 . 0)
                 (6 . "Other") (91 . 7)
                 (7 . "ACFD_FIELD_VALUE") (91 . 99))
        patched (SRF:Patch source 63))
  (SRFT:Assert (equal (SRFT:Options patched) '(63 63 7 99)) "Only both evaluation options change")
  (SRFT:Assert (not (SRF:Code patched)) "entmod payload omits all FIELD code groups")
  (SRFT:Assert (equal (SRFT:Options source) '(0 0 7 99)) "Original snapshot remains unchanged")
  (SRFT:Assert (= (SRF:Property source) "Revision") "CustomDP property parsed without editing code")
  (setq enabled '((0 . "FIELD") (91 . 16)
                  (6 . "ACAD_ROUNDTRIP_2008_FIELD_EVALOPTION") (91 . 0)
                  (6 . "Other") (91 . 7) (7 . "ACFD_FIELD_VALUE") (91 . 99))
        patched (SRF:Patch enabled 16))
  (SRFT:Assert (equal (SRFT:Options patched) '(16 16 7 99)) "Nonzero evaluation policy is preserved")
  (SRFT:Assert (equal (SRF:Patch patched 16) patched) "Second patch is idempotent")
  (princ "\nPASS: ACTUALIZAR-VINETA DXF option and code-preservation regressions.")
  T)
(princ)

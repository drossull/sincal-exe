(vl-load-com)
(defun SUBT:Check (condition message)
  (write-line (strcat (if condition "PASS " "FAIL ") message) SUBT:report)
  (if (not condition) (setq SUBT:failures (1+ SUBT:failures))))

(defun SUBT:Static (doc db / old new ref attr before b)
  (setq old (vla-Add (vla-get-Blocks doc) (vlax-3d-point '(0 0 0)) "UB STATIC")
        new (vla-Add (vla-get-Blocks db) (vlax-3d-point '(0 0 0)) "UB STATIC"))
  (vla-AddCircle old (vlax-3d-point '(0 0 0)) 5.0)
  (vla-AddLine new (vlax-3d-point '(0 0 0)) (vlax-3d-point '(100 50 0)))
  (foreach b (list old new)
    (vla-AddAttribute b 2.0 0 "Quantity" (vlax-3d-point '(0 0 0)) "QTY" "DEFAULT"))
  (setq ref (vla-InsertBlock (vla-get-ModelSpace doc) (vlax-3d-point '(200 300 0))
              "UB STATIC" 2 3 1 0.72)
        attr (car (vlax-invoke ref 'GetAttributes)))
  (vla-put-TextString attr "172 editable")
  (setq before (SUB:Attributes ref))
  (SUBT:Check (= 1 (SUB:Redefine doc db "UB STATIC")) "static block with spaces and nonuniform scale")
  (SUBT:Check (= "AcDbLine" (vla-get-ObjectName (vla-Item old 0))) "static geometry replaced")
  (SUBT:Check (equal before (SUB:Attributes ref)) "editable literal attribute retained")
  (vl-file-delete SUB:tempfile))

(defun SUBT:Run (/ doc db source arr block ref ref2 before count props)
  (defun SUB:Fail (message)
    (write-line message SUBT:report)
    (if (and (boundp 'row) row)
      (progn
        (write-line (vl-princ-to-string (cdr row)) SUBT:report)
        (write-line (vl-princ-to-string (SUB:Placement (car row))) SUBT:report)
        (write-line (vl-princ-to-string (SUB:Attributes (car row))) SUBT:report)))
    (exit))
  (setq SUBT:failures 0 doc (vla-get-ActiveDocument (vlax-get-acad-object))
        db (SUB:Dbx))
  (vla-Open db (strcat (getenv "SINCAL_TEST_ROOT") "/masters/FORMATOS ANOTATIVOS ACAD_2025.dwg"))
  (setvar "FILEDIA" 0) (setvar "ATTREQ" 0)
  (SUBT:Static doc db)
  (setq source (vla-Item (vla-get-Blocks db) "NIVEL")
        arr (vlax-make-safearray vlax-vbObject '(0 . 0)))
  (vlax-safearray-put-element arr 0 source)
  (vla-CopyObjects db arr (vla-get-Blocks doc))
  (setq block (vla-Item (vla-get-Blocks doc) "NIVEL") count (vla-get-Count block))
  ;; A deliberate obsolete entity proves that the definition actually changes.
  (vla-AddCircle block (vlax-3d-point '(700 800 0)) 42.0)
  (setq ref (vla-InsertBlock (vla-get-ModelSpace doc) (vlax-3d-point '(10 20 0)) "NIVEL" 2 2 2 0.42)
        ref2 (vla-InsertBlock (vla-get-PaperSpace doc) (vlax-3d-point '(50 60 0)) "NIVEL" 1 1 1 0.2))
  (foreach p (vlax-invoke ref 'GetDynamicBlockProperties)
    (if (and (= :vlax-false (vla-get-ReadOnly p))
             (= vlax-vbDouble (vlax-variant-type (vla-get-Value p)))
             (wcmatch (strcase (vla-get-PropertyName p)) "*DIST*,*ALT*,*LONG*"))
      (vla-put-Value p (vlax-make-variant 25.0 vlax-vbDouble))))
  (setq before (SUB:References doc "NIVEL"))
  (setq SUBT:oldcount (vla-get-Count block))
  (command "_.UNDO" "_Begin")
  (vla-Regen doc 1)
  (setq before (SUB:References doc "NIVEL"))
  (setvar "FILEDIA" 0) (setvar "ATTREQ" 0)
  (SUBT:Check (= 2 (SUB:Redefine doc db "NIVEL")) "two references across layouts")
  (SUBT:Check (= count (vla-get-Count (vla-Item (vla-get-Blocks doc) "NIVEL"))) "obsolete geometry removed")
  (foreach row before
    (SUBT:Check (equal (cadr row) (SUB:Placement (car row)) 1e-8) "handle/placement retained")
    (SUBT:Check (equal (caddr row) (SUB:Attributes (car row))) "attributes retained")
    (setq props (SUB:Dynamic (car row)))
    (foreach prop (cadddr row)
      (SUBT:Check (and (assoc (car prop) props)
        (equal (vlax-variant-value (cdr prop))
          (vlax-variant-value (cdr (assoc (car prop) props))) 1e-8))
        (strcat "dynamic value " (car prop)))))
  (vlax-release-object db)
  (if SUB:tempfile (vl-file-delete SUB:tempfile))
  (command "_.UNDO" "_End")
  (write-line (strcat "DONE failures=" (itoa SUBT:failures)) SUBT:report)
  (close SUBT:report))

(defun SUBT:CheckUndo ()
  (SUBT:Check (= SUBT:oldcount
    (vla-get-Count (vla-Item (vla-get-Blocks (vla-get-ActiveDocument (vlax-get-acad-object))) "NIVEL")))
    "U restores obsolete definition")
  (write-line (strcat "UNDO DONE failures=" (itoa SUBT:failures)) SUBT:report)
  (close SUBT:report))

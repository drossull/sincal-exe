;;; Run after the regression in a disposable drawing, with SINCAL_TEST_ROOT set.
(defun SCMT:Text (obj tag) (vla-get-TextString (cdr (assoc tag (SCM:Attrs obj)))))
(defun SCMT:Mask (att / ed inside data p)
  (foreach p (entget (vlax-vla-object->ename att))
    (if (= 101 (car p)) (setq inside T))
    (if inside (setq data (cons p data))))
  (and (= 3 (cdr (assoc 90 data))) (equal 1.2 (cdr (assoc 45 data)) 1e-8)))
(defun SCMT:DynamicSetup (/ space obj p circle ed)
  (setq space (vla-get-ModelSpace (SCM:Doc)))
  (setq SCMT:Table (vla-AddTable space (vlax-3d-point '(0 40 0)) 4 4 3.0 12.0))
  (foreach item '((0 0 "ARMADURAS") (1 0 "MARCA") (1 1 "#") (1 2 "%%c") (1 3 "@")
                 (2 0 "1") (2 1 "163") (2 2 "8") (2 3 "20")
                 (3 0 "12") (3 1 "24") (3 2 "12") (3 3 "15"))
    (vla-SetText SCMT:Table (car item) (cadr item) (caddr item)))
  (setq SCMT:Original (vla-InsertBlock space (vlax-3d-point '(0 0 0)) (SCM:BasicDefinition) 2.5 2.5 2.5 0.0))
  (SCM:Bind SCMT:Original SCMT:Table 2)
  (SCM:Evaluate (list SCMT:Original))
  (SCMT:Assert (= :vlax-true (vla-get-IsDynamicBlock SCMT:Original)) "native dynamic definition")
  (SCMT:Assert (SCMT:Mask (cdr (assoc "MARCA" (SCM:Attrs SCMT:Original)))) "full description background mask 1.2")
  (SCMT:Assert (SCMT:Mask (cdr (assoc "MARCA_CANT" (SCM:Attrs SCMT:Original)))) "quantity description background mask 1.2")
  (SCMT:Assert (= "163 %%c8@20" (SCMT:Text SCMT:Original "MARCA_CANT")) "quantity precedes diameter")
  (foreach att (SCM:Attrs SCMT:Original)
    (SCMT:Assert (= "ROMAND" (strcase (vla-get-StyleName (cdr att)))) (strcat "RomanD " (car att))))
  (vlax-for obj (vla-item (vla-get-Blocks (SCM:Doc)) "SINCAL_MARCA_SC_V3")
    (if (= "AcDbCircle" (vla-get-ObjectName obj)) (setq circle (= 1 (vla-get-Color obj)))))
  (SCMT:Assert circle "circle ACI 1")
  (setq ed (entget (vlax-vla-object->ename (vla-item (vla-get-Blocks (SCM:Doc)) "SINCAL_MARCA_SC_V3")) '("AcadAnnotative")))
  (SCMT:Assert (assoc -3 ed) "annotative block metadata")
  (foreach p (vlax-invoke SCMT:Original 'GetDynamicBlockProperties)
    (princ (list (vla-get-PropertyName p) (vlax-get p 'Value) (vlax-get p 'AllowedValues)))
    (if (wcmatch (strcase (vla-get-PropertyName p)) "*FLIP*") (setq SCMT:Flip p))
    (if (wcmatch (strcase (vla-get-PropertyName p)) "*VISIBILITY*") (setq SCMT:Visibility p)))
  (SCMT:Assert (and SCMT:Flip SCMT:Visibility) "native flip and visibility controls")
  (vla-put-Value SCMT:Flip (vlax-make-variant 1 vlax-vbInteger))
  (vla-put-Value SCMT:Visibility (vlax-make-variant "CON_CANTIDAD" vlax-vbString))
  (SCMT:Assert (= 1 (vlax-get SCMT:Flip 'Value)) "flip can switch")
  (SCMT:Assert (= "CON_CANTIDAD" (vlax-get SCMT:Visibility 'Value)) "visibility can switch")
  (SCMT:Assert (SCMT:Mask (cdr (assoc "MARCA_CANT" (SCM:Attrs SCMT:Original)))) "mask survives flip")
  (SCMT:Assert (equal 0.0 (vla-get-Rotation (cdr (assoc "MARCA_CANT" (SCM:Attrs SCMT:Original))))) "flipped description remains upright")
  (setq SCMT:Copy (vla-Copy SCMT:Original))
  (vla-Move SCMT:Copy (vlax-3d-point '(0 0 0)) (vlax-3d-point '(0 -15 0)))
  (SCM:Watch)
  (princ))
(SCMT:DynamicSetup)

;;; Disposable native CAD session only; leaves fixtures for scripted commands.
(defun SCMDT:Text (obj tag) (vla-get-TextString (cdr (assoc tag (SCM:Attrs obj)))))
(defun SCMDT:ManualP (obj)
  (and (= "172" (SCMDT:Text obj "CANT_TOTAL")) (= "L=368" (SCMDT:Text obj "LARGO"))))
(defun SCMDT:MaskP (att / data inside pair)
  (foreach pair (entget (vlax-vla-object->ename att))
    (if (= 101 (car pair)) (setq inside T))
    (if inside (setq data (cons pair data))))
  (and (= 3 (cdr (assoc 90 data))) (equal 1.2 (cdr (assoc 45 data)) 1e-8)))
(setq SCMDT:Table (vla-AddTable (vla-get-ModelSpace (SCM:Doc)) (vlax-3d-point '(0 60 0)) 4 4 3.0 12.0))
(foreach item '((0 0 "DESPIECE") (1 0 "MARCA") (1 1 "#") (1 2 "%%c") (1 3 "@")
               (2 0 "7a") (2 2 "12") (3 0 "8") (3 2 "16"))
  (vla-SetText SCMDT:Table (car item) (cadr item) (caddr item)))
;;; Isolate graphical table picking; all other MARCA-DE prompts run natively.
(defun SCM:PickTable () SCMDT:Table)
(defun SCMDT:Check (/ obj property attrs ed)
  (setq SCMDT:Original (vlax-ename->vla-object (entlast)) obj SCMDT:Original)
  (SCMT:Assert (SCM:DetailP obj) "MARCA-DE creates detail variant")
  (SCMT:Assert (null (assoc "MARCA_CANT" (SCM:Attrs obj))) "no table quantity or spacing description")
  (SCMT:Assert (= "7a" (SCMDT:Text obj "XX")) "detail mark linked")
  (SCMT:Assert (= "%%c12" (SCMDT:Text obj "MARCA")) "detail diameter linked without spacing")
  (SCMT:Assert (= "172" (SCMDT:Text obj "CANT_TOTAL")) "total comes from manual prompt")
  (SCMT:Assert (= "L=368" (SCMDT:Text obj "LARGO")) "length comes from manual prompt with prefix")
  (SCMT:Assert (SCM:Healthy obj (SCM:Resolve obj)) "detail fields healthy with blank B and D")
  (SCMT:Assert (SCM:DetailEditableP obj) "manual attributes are single-line for Properties")
  ;; Emulate already inserted V1 references; repair must retain user data.
  (foreach tag '("CANT_TOTAL" "LARGO")
    (vla-put-MTextAttribute (cdr (assoc tag (SCM:Attrs obj))) :vlax-true)
    (vla-UpdateMTextAttribute (cdr (assoc tag (SCM:Attrs obj)))))
  (SCMT:Assert (not (SCM:Healthy obj (SCM:Resolve obj))) "legacy multiline attributes require repair")
  (SCM:SyncOne obj)
  (SCMT:Assert (and (SCM:DetailEditableP obj) (SCMDT:ManualP obj)
    (SCM:Healthy obj (SCM:Resolve obj))) "repair exposes legacy values in Properties without resetting them")
  (SCMT:Assert (SCM:RowIssue SCMDT:Table 2) "view still requires quantity and spacing")
  (SCMT:Assert (= :vlax-true (vla-get-IsDynamicBlock obj)) "detail keeps native flip")
  (foreach property (vlax-invoke obj 'GetDynamicBlockProperties)
    (if (wcmatch (strcase (vla-get-PropertyName property)) "*FLIP*") (setq SCMDT:Flip property)))
  (SCMT:Assert SCMDT:Flip "detail flip property present")
  (vla-put-Value SCMDT:Flip (vlax-make-variant 1 vlax-vbInteger))
  (SCMT:Assert (= 1 (vlax-get SCMDT:Flip 'Value)) "detail flip switches")
  (foreach att (SCM:Attrs obj)
    (SCMT:Assert (= "ROMAND" (strcase (vla-get-StyleName (cdr att)))) (strcat "detail font " (car att))))
  (SCMT:Assert (SCMDT:MaskP (cdr (assoc "MARCA" (SCM:Attrs obj)))) "linked diameter retains mask")
  (SCMT:Assert (SCM:DetailEditableP obj) "manual attributes stay single-line after flip")
  (foreach tag '("MARCA" "CANT_TOTAL" "LARGO")
    (SCMT:Assert (equal 0.0 (vla-get-Rotation (cdr (assoc tag (SCM:Attrs obj)))) 1e-8) (strcat "upright after flip " tag)))
  (setq ed (entget (vlax-vla-object->ename (vla-item (vla-get-Blocks (SCM:Doc)) "SINCAL_MARCA_DE_V2")) '("AcadAnnotative")))
  (SCMT:Assert (assoc -3 ed) "detail annotative metadata")
  (vla-SetText SCMDT:Table 2 2 "12.5")
  (SCM:Evaluate (list obj))
  (SCMT:Assert (= "%%c12.5" (SCMDT:Text obj "MARCA")) "diameter update uses one decimal")
  (SCMT:Assert (SCMDT:ManualP obj) "table update preserves manual total and length")
  (vla-InsertRows SCMDT:Table 2 3.0 1)
  (SCMT:Assert (= 3 (cadr (SCM:Resolve obj))) "detail identity survives inserted row")
  (SCM:SyncOne obj)
  (SCMT:Assert (and (SCM:Healthy obj (SCM:Resolve obj)) (SCMDT:ManualP obj)) "detail repair preserves manual attributes")
  (setq SCMDT:Copy (vla-Copy obj))
  (vla-Move SCMDT:Copy (vlax-3d-point '(0 0 0)) (vlax-3d-point '(0 -15 0)))
  (SCM:Watch))
(defun c:SCMDT-EDIT () (SCM:PutText (cdr (assoc "XX" (SCM:Attrs SCMDT:Copy))) "8") (princ))
(defun c:SCMDT-MANUAL ()
  (SCM:PutText (cdr (assoc "CANT_TOTAL" (SCM:Attrs SCMDT:Copy))) "200")
  (SCM:PutText (cdr (assoc "LARGO" (SCM:Attrs SCMDT:Copy))) "L=450") (princ))
(defun c:SCMDT-BAD () (SCM:PutText (cdr (assoc "XX" (SCM:Attrs SCMDT:Copy))) "99") (princ))

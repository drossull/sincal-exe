(vl-load-com)
(setq vg-doc (vla-get-ActiveDocument (vlax-get-acad-object))
      vg-name (strcat "VI" (chr 209) "ETA G130")
      vg-blocks (vla-get-Blocks vg-doc)
      vg-origin (vlax-3d-point '(0.0 0.0 0.0)))
(setq vg-def (vla-Add vg-blocks vg-origin vg-name))
(vla-AddLine vg-def vg-origin (vlax-3d-point '(1.0 0.0 0.0)))
(vla-Add vg-blocks vg-origin "VINETA G130")
(vla-Add vg-blocks vg-origin (strcat "VI" (chr 209) "ETA G131"))
(vla-Add vg-blocks vg-origin (strcat "OTRA VI" (chr 209) "ETA G130"))
(setq vg-model (vla-get-ModelSpace vg-doc)
      vg-paper (vla-get-Block (vla-Item (vla-get-Layouts vg-doc) "Layout1")))
(defun VGT:Insert (space name) (vla-InsertBlock space vg-origin name 1.0 1.0 1.0 0.0))
(setq vg-a (VGT:Insert vg-model vg-name)
      vg-b (VGT:Insert vg-model vg-name)
      vg-c (VGT:Insert vg-paper vg-name)
      vg-other (VGT:Insert vg-model "VINETA G130")
      vg-locked (VGT:Insert vg-model vg-name)
      vg-layer (vla-Add (vla-get-Layers vg-doc) "VG_LOCKED"))
(VGT:Insert vg-paper (strcat "VI" (chr 209) "ETA G131"))
(setq vg-unrelated (VGT:Insert vg-model (strcat "OTRA VI" (chr 209) "ETA G130")))
(vla-put-Layer vg-locked "VG_LOCKED")
(vla-put-Lock vg-layer :vlax-true)
(setq vg-failures 0)
(defun VGT:Assert (ok label)
  (if (not ok) (setq vg-failures (1+ vg-failures)))
  (write-line (strcat (if ok "PASS " "FAIL ") label) vg-report))
(setq vg-result (VG:Remove vg-doc))
(VGT:Assert (equal vg-result '(4 1)) "multiple projects, all layouts, locked layer")
(VGT:Assert (not (vlax-erased-p vg-unrelated)) "name must start with prefix")
(VGT:Assert (not (vlax-erased-p vg-other)) "similar name retained")
(VGT:Assert (not (vlax-erased-p vg-locked)) "locked reference retained")
(vla-put-Lock vg-layer :vlax-false)
(princ)

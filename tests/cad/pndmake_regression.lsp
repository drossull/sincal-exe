(defun PNDMT:Assert (ok label)
  (if (not ok) (setq PNDMT:Failures (1+ PNDMT:Failures)))
  (write-line (strcat (if ok "PASS " "FAIL ") label) PNDMT:Report))
(setq PNDMT:Failures 0)
(foreach percent '(0.0 10.0 -10.0 100.0 -100.0 250.0)
  (foreach end '((10.0 0.0 0.0) (-10.0 0.0 0.0) (0.0 10.0 0.0) (8.0 6.0 0.0))
    (setq entity (entmakex (list '(0 . "LINE") '(10 0.0 0.0 0.0) (cons 11 end)))
          object (vlax-ename->vla-object entity))
    (PNDM:Apply object '(0.0 0.0 0.0) '(0.0 0.0 0.0) end percent)
    (setq result (cdr (assoc 11 (entget entity))))
    (PNDMT:Assert (equal percent (* 100.0 (/ (cadr result) (car result))) 1e-8) "absolute slope")
    (PNDMT:Assert (equal 10.0 (distance '(0.0 0.0 0.0) result) 1e-8) "length retained")
    (PNDMT:Assert (equal '(0.0 0.0 0.0) (cdr (assoc 10 (entget entity))) 1e-8) "base fixed")))
(PNDMT:Assert (vl-catch-all-error-p (vl-catch-all-apply 'PNDM:Delta '((0.0 0.0 0.0) (0.0 0.0 0.0) 10.0))) "zero axis rejected")
(PNDMT:Assert (vl-catch-all-error-p (vl-catch-all-apply 'PNDM:Delta '((0.0 0.0 0.0) (10.0 0.0 1.0) 10.0))) "out of plane rejected")
;; A bent polyline rotates rigidly, only the reference segment gets the slope.
(setq entity (entmakex '((0 . "LWPOLYLINE") (100 . "AcDbEntity")
  (100 . "AcDbPolyline") (90 . 3) (70 . 0)
  (10 0.0 0.0) (10 10.0 0.0) (10 10.0 5.0)))
  object (vlax-ename->vla-object entity))
(PNDM:Apply object '(0.0 0.0 0.0) '(0.0 0.0 0.0) '(10.0 0.0 0.0) -10.0)
(PNDMT:Assert (equal 15.0 (vla-get-Length object) 1e-8) "polyline length retained")
(setq result (vlax-curve-getPointAtParam object 1.0))
(PNDMT:Assert (equal -0.1 (/ (cadr result) (car result)) 1e-8) "polyline reference slope")
;; Rotated UCS: work in the UCS plane, even with non-default angle settings.
(command "_.UCS" "_X" "35")
(setvar "ANGBASE" 0.5)
(setvar "ANGDIR" 1)
(setq entity (entmakex (list '(0 . "LINE")
  (cons 10 (trans '(0.0 0.0 0.0) 1 0)) (cons 11 (trans '(10.0 0.0 0.0) 1 0))))
  object (vlax-ename->vla-object entity))
(PNDM:Apply object '(0.0 0.0 0.0) '(0.0 0.0 0.0) '(10.0 0.0 0.0) 10.0)
(setq result (trans (cdr (assoc 11 (entget entity))) 0 1))
(PNDMT:Assert (and (equal 0.1 (/ (cadr result) (car result)) 1e-8)
  (equal 0.0 (caddr result) 1e-8)) "tilted UCS and custom angle settings")
(command "_.UCS" "_World")
(setvar "ANGBASE" 0.0)
(setvar "ANGDIR" 0)
;; Exercise the real command via implied selection and its actual prompts.
(setq entity (entmakex '((0 . "LINE") (10 20.0 0.0 0.0) (11 30.0 0.0 0.0))))
(sssetfirst nil (ssadd entity))
(princ)

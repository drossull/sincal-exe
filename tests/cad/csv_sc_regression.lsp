(setq CSVT:failures 0)
(defun CSVT:Assert (value message)
  (write-line (strcat (if value "PASS " "FAIL ") message) CSVT:report)
  (if (not value) (setq CSVT:failures (1+ CSVT:failures))))
(defun CSVT:Run (/ data doc table style row col value values point SCSV:table header sample)
  (CSVT:Assert (equal (SCSV:Fields "1;\"11_1\";;\"a; b\";\"a\"\"b\";")
                     '("1" "11_1" "" "a; b" "a\"b" "")) "quoted fields and empty cells")
  (setq data (SCSV:Parse (SCSV:ReadText CSVT:csv "windows-1252")))
  (CSVT:Assert (= (length (cadr data)) 42) "42 source records, no report furniture")
  (CSVT:Assert (= (length (car data)) 16) "16 columns in source order")
  (CSVT:Assert (equal (caddr data) '("15384" "kg")) "declared total preserved")
  (if CSVT:xsr
    (CSVT:Assert (equal data (SCSV:Parse (SCSV:ReadText CSVT:xsr "windows-1252"))) "XSR and CSV exactly equal, including empty cells"))
  (setq header "Cant.;diametro;Long.;Pos;Calidad;Forma;Peso/ud;Peso;A max;A min;B max;B min;C max;C min;TOTAL MIN;TOTAL MAX"
        sample "1;12;5449;EE-24(?);A630-420H;11_1;4.84;4.8;450;450;95;95;;;545;545")
  (CSVT:Assert (= 2 (length (cadr (SCSV:Parse (strcat header "\n" sample "\n" header "\n" sample))))) "repeated page header omitted")
  (CSVT:Assert (vl-catch-all-error-p (vl-catch-all-apply 'SCSV:Parse (list (strcat header "\n1;12;3")))) "short row rejected")
  (CSVT:Assert (vl-catch-all-error-p (vl-catch-all-apply 'SCSV:Parse (list (strcat header "\n" sample "\nunknown row")))) "unknown row rejected")
  (CSVT:Assert (vl-catch-all-error-p (vl-catch-all-apply 'SCSV:Fields '("1;\"unclosed"))) "unclosed quote rejected")
  (CSVT:Assert (equal (SCSV:Literal "%<x> {y}\\z") "\\U+0025<x> \\{y\\}\\\\z") "MText and CAD field syntax escaped")
  (CSVT:Assert (= "11_1" (nth 5 (car (cadr (SCSV:Parse
    (SCSV:ReadText (strcat (getenv "SINCAL_TEST_ROOT") "/tests/cad/csv_sc_utf8.csv") "utf-8")))))) "UTF8 input supported")
  (setq doc (vla-get-ActiveDocument (vlax-get-acad-object)))
  (setvar "TILEMODE" 1)
  (setq table (SCSV:Build doc data '(0 0 0) 1.0)
        style (vla-Item (vla-Item (vla-get-Dictionaries doc) "ACAD_TABLESTYLE") "TENSIONES"))
  (CSVT:Assert (= (vla-get-StyleName table) "TENSIONES") "master TENSIONES imported")
  (CSVT:Assert (= (vla-GetTextStyle style 1) "RomanD") "master RomanD font")
  (CSVT:Assert (= (vla-get-Rows table) 45) "title, header, 42 records, total")
  (CSVT:Assert (= (vla-get-Columns table) 16) "table column count")
  (setq row 2)
  (repeat 42
    (CSVT:Assert (and (equal (vla-GetRowHeight table row) (vla-GetMinimumRowHeight table row) 1e-6)
                     (< (vla-GetRowHeight table row) 7.0)) "compact single-line data row")
    (setq row (1+ row)))
  (setq row 1)
  (foreach values (cons (car data) (cadr data))
    (setq col 0)
    (foreach value values
      (CSVT:Assert (= (vla-GetText table row col) value)
        (strcat "cell " (itoa row) "," (itoa col)))
      (setq col (1+ col)))
    (setq row (1+ row)))
  (CSVT:Assert (= (vla-GetText table row 7) "15384 kg") "total in weight column")
  (CSVT:Assert (= (vla-GetText table row 8) "") "kg does not pollute A max")
  (CSVT:Assert (equal (vla-GetCellTextHeight table 2 0) 2.5 1e-6) "native text height")
  (vla-SaveAs doc CSVT:output)
  (setvar "TILEMODE" 0)
  (setq table (SCSV:Build doc data '(20 200 0) 0.025))
  (CSVT:Assert (= (vla-get-OwnerID table) (vla-get-ObjectID (vla-get-PaperSpace doc))) "current paper space")
  (CSVT:Assert (equal (vla-GetCellTextHeight table 2 0) 0.0625 1e-6) "scaled text height")
  (vla-SetText table 2 0 "141")
  (CSVT:Assert (= (vla-GetText table 2 0) "141") "editable native cell")
  (write-line (strcat "DONE failures=" (itoa CSVT:failures)) CSVT:report)
  (close CSVT:report) (setq CSVT:report nil))
(CSVT:Run)

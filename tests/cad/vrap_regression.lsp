;;; Native command regression. Run only in disposable drawings through
;;; tools/cad/test_vrap_native.py; never use the user's active document.
(vl-load-com)

(defun SVR:Log (message / stream)
  (setq stream (open SVR:report "a"))
  (write-line message stream)
  (close stream))

(defun SVR:Assert (condition message)
  (if (not condition) (setq SVR:failures (1+ SVR:failures)))
  (SVR:Log (strcat (if condition "PASS " "FAIL ") SVR:case " " message)))

(defun SVR:Finish ()
  (SVR:Log (strcat "PHASE_DONE " SVR:case " failures=" (itoa SVR:failures))))

(defun SVR:Floating (layout / result obj data)
  (vlax-for obj (vla-get-Block layout)
    (if (= "AcDbViewport" (vla-get-ObjectName obj))
      (progn
        (setq data (entget (vlax-vla-object->ename obj)))
        (if (> (cdr (assoc 69 data)) 1)
          (setq result (cons obj result))))))
  result)

(defun SVR:Array (value)
  (vlax-safearray->list (vlax-variant-value value)))

(defun SVR:Prepare (phase report / *error* layout p1 p2)
  (setq SVR:case phase SVR:report report SVR:failures 0)
  (defun *error* (message)
    (SVR:Assert nil (strcat "fixture error: " message))
    (SVR:Finish)
    (princ))
  (setq SVR:app (vlax-get-acad-object)
        SVR:doc (vla-get-ActiveDocument SVR:app)
        SVR:layout "VRAP_NATIVE_TEST"
        SVR:scale-name (if (= phase "METRES") "SVR_METRES_100" "SVR_MM_100")
        SVR:factor (if (= phase "METRES") 10.0 0.01)
        SVR:width (if (= phase "METRES") 200.0 2.0)
        SVR:height (if (= phase "METRES") 100.0 1.0)
        p1 '(1000.0 2000.0 0.0)
        p2 (if (= phase "METRES") '(1020.0 2010.0 0.0) '(1200.0 2100.0 0.0)))
  (setvar "CMDECHO" 0)
  (setvar "TILEMODE" 0)
  (vla-put-MSpace SVR:doc :vlax-false)
  (setq layout (vla-Add (vla-get-Layouts SVR:doc) SVR:layout))
  (vla-put-ActiveLayout SVR:doc layout)
  (setvar "CTAB" SVR:layout)
  (vla-Regen SVR:doc 1)
  ;; ZWCAD can defer its automatic default viewport until the first return
  ;; from Model. Materialize it before recording the fixture's handles.
  (setvar "TILEMODE" 1)
  (setvar "TILEMODE" 0)
  (setvar "CTAB" SVR:layout)
  (vla-put-MSpace SVR:doc :vlax-false)
  (vla-Regen SVR:doc 1)
  (command "_.UCS" "_World")
  (setq SVR:before (mapcar 'vla-get-Handle (SVR:Floating layout)))
  ;; The command must remember this layout even though we return to Model.
  (setvar "TILEMODE" 1)
  (setvar "UCSFOLLOW" 0)
  (command "_.UCS" "_World")
  (command "_.PLAN" "_World")
  (if (= phase "ROTATED")
    (progn
      (command "_.UCS" "_Z" "30")
      (command "_.PLAN" "_Current")))
  (command "_.-SCALELISTEDIT" "_Add" SVR:scale-name
    (if (= phase "METRES") "1000:100" "1:100") "_Exit")
  (setvar "CANNOSCALE" SVR:scale-name)
  (setq SVR:center (trans (mapcar '(lambda (a b) (/ (+ a b) 2.0)) p1 p2) 1 0)
        SVR:twist (getvar "VIEWTWIST")
        SVR:direction (trans (getvar "VIEWDIR") 1 0 T))
  (vla-AddLine (vla-get-ModelSpace SVR:doc)
    (vlax-3d-point (trans p1 1 0)) (vlax-3d-point (trans p2 1 0)))
  (setvar "OSMODE" 35)
  (setvar "CMDECHO" 1)
  (setvar "ANNOAUTOSCALE" 4)
  (setq SVR:variables (mapcar '(lambda (key) (cons key (getvar key)))
    '("OSMODE" "CMDECHO" "ANNOAUTOSCALE")))
  (SVR:Assert (equal SVR:factor (getvar "CANNOSCALEVALUE") 1e-10)
    "fixture annotation ratio")
  (SVR:Log (strcat "FIXTURE_READY " phase))
  (princ))

(defun SVR:Check (/ *error* layout added obj value view-center pair)
  (defun *error* (message)
    (SVR:Assert nil (strcat "check error: " message))
    (vl-catch-all-apply 'vla-put-MSpace (list SVR:doc :vlax-false))
    (SVR:Finish)
    (princ))
  (foreach pair SVR:variables
    (SVR:Assert (equal (cdr pair) (getvar (car pair)))
      (strcat "restores " (car pair))))
  (setq layout (vla-Item (vla-get-Layouts SVR:doc) SVR:layout)
        added (vl-remove-if '(lambda (vp) (member (vla-get-Handle vp) SVR:before))
          (SVR:Floating layout)))
  (if (= SVR:case "CANCEL")
    (SVR:Assert (null added) "cancel at paper insertion leaves no viewport")
    (progn
      (SVR:Assert (= 1 (length added)) "creates exactly one viewport")
      (SVR:Assert (= SVR:layout (getvar "CTAB")) "uses last active paper layout")
      (SVR:Assert (and (= 0 (getvar "TILEMODE")) (= 1 (getvar "CVPORT")))
        "finishes in paper space")
      (if (= 1 (length added))
        (progn
          (setq obj (car added))
          (SVR:Log (strcat "VIEWPORT " SVR:case " "
            (vl-princ-to-string (list
              (cons 'width (vla-get-Width obj)) (cons 'height (vla-get-Height obj))
              (cons 'scale (vla-get-CustomScale obj))
              (cons 'target (SVR:Array (vla-get-Target obj)))
              (cons 'twist (vla-get-TwistAngle obj))))))
          (SVR:Assert (equal SVR:width (vla-get-Width obj) 1e-7) "paper width")
          (SVR:Assert (equal SVR:height (vla-get-Height obj) 1e-7) "paper height")
          (SVR:Assert (equal SVR:factor (vla-get-CustomScale obj) 1e-10) "exact viewport scale")
          (SVR:Assert (equal (list (+ 20.0 (/ SVR:width 2.0))
              (+ 30.0 (/ SVR:height 2.0)) 0.0)
            (SVR:Array (vla-get-Center obj)) 1e-7) "paper insertion lower-left")
          (SVR:Assert (= :vlax-true (vla-get-DisplayLocked obj)) "viewport locked")
          (SVR:Assert (equal SVR:twist (vla-get-TwistAngle obj) 1e-8) "view twist retained")
          (vla-Display obj :vlax-true)
          ;; The 2x1 paper-unit fixture is smaller than a few display pixels.
          ;; Enlarge only the paper view so CAD can activate it for inspection.
          (if (vl-catch-all-error-p (vl-catch-all-apply 'vla-ZoomCenter
                (list SVR:app (vla-get-Center obj) (* 1.5 SVR:height))))
            (command-s "_.ZOOM" "_Center" "_non"
              (trans (SVR:Array (vla-get-Center obj)) 0 1) (* 1.5 SVR:height)))
          (vla-put-MSpace SVR:doc :vlax-true)
          (vla-put-ActivePViewport SVR:doc obj)
          (SVR:Assert (> (getvar "CVPORT") 1) "inspection activates model viewport")
          (SVR:Assert (= SVR:scale-name (getvar "CANNOSCALE")) "annotation scale name retained")
          (SVR:Assert (equal SVR:factor (getvar "CANNOSCALEVALUE") 1e-10)
            "viewport annotation ratio")
          (setq value (getvar "VIEWCTR")
                ;; VIEWCTR is expressed in the current UCS, not the DCS
                ;; used by the viewport's DXF group 12.
                view-center (trans (list (car value) (cadr value) 0.0) 1 0))
          (SVR:Log (strcat "CENTER " SVR:case " expected=" (vl-princ-to-string SVR:center)
            " actual=" (vl-princ-to-string view-center)))
          (SVR:Assert (equal SVR:center view-center 1e-6) "model rectangle centered in viewport")
          (SVR:Assert (equal SVR:direction (trans (getvar "VIEWDIR") 1 0 T) 1e-8)
            "view direction retained")
          (vla-put-MSpace SVR:doc :vlax-false)))))
  (SVR:Finish)
  (princ))

(princ)

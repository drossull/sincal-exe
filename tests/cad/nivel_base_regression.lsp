;;; Native NIVEL_MM field regression. Run only in disposable documents.
;;; UPDATEBLOCK.lsp must be loaded by the runner before SNB:Run.
(vl-load-com)
(defun SNB:Log (message) (write-line message SNB:report))
(defun SNB:Check (condition message)
  (if (not condition) (setq SNB:failures (1+ SNB:failures)))
  (SNB:Log (strcat (if condition "PASS " "FAIL ") message)))
(defun SNB:Attr (ref tag / found att)
  (foreach att (vlax-invoke ref 'GetAttributes)
    (if (= tag (vla-get-TagString att)) (setq found att))) found)
(defun SNB:Prop (ref name / found prop)
  (foreach prop (vlax-invoke ref 'GetDynamicBlockProperties)
    (if (= name (vla-get-PropertyName prop)) (setq found prop))) found)
(defun SNB:Set (ref name value / prop)
  (setq prop (SNB:Prop ref name))
  (if (not prop) (progn (SNB:Log (strcat "ERROR missing property " name)) (exit)))
  (vla-put-Value prop (vlax-make-variant value (vlax-variant-type (vla-get-Value prop)))))
(defun SNB:Value (ref) (vla-get-TextString (SNB:Attr ref "NIVEL")))
(defun SNB:Base (ref value) (vla-put-TextString (SNB:Attr ref "BASE") value))
(defun SNB:Evaluate (ref)
  (command "_.UPDATEFIELD" (vlax-vla-object->ename ref) "")
  (vla-Regen SNB:doc 1))
(defun SNB:Data (en / data)
  (if en (progn (setq data (vl-catch-all-apply 'entget (list en)))
    (if (not (vl-catch-all-error-p data)) data))))
(defun SNB:Handle (en / data)
  (if (setq data (SNB:Data en)) (cdr (assoc 5 data)) "nil"))
(defun SNB:DumpField (field depth / data item target owner)
  (if (and field (< depth 12) (setq data (entget field)))
    (progn
      (SNB:Log (strcat "FIELD depth=" (itoa depth) " handle=" (SNB:Handle field)
        " evaluator=" (vl-princ-to-string (cdr (assoc 1 data)))
        " code=" (vl-princ-to-string (cdr (assoc 2 data)))))
      (foreach item data
        (cond
          ((= 331 (car item))
           (setq target (SNB:Data (cdr item)) owner (cdr (assoc 330 target)))
           (SNB:Log (strcat "TARGET handle=" (SNB:Handle (cdr item))
             " type=" (vl-princ-to-string (cdr (assoc 0 target)))
             " tag=" (vl-princ-to-string (cdr (assoc 2 target)))
             " text=" (vl-princ-to-string (cdr (assoc 1 target)))
             " owner=" (SNB:Handle owner))))
          ((= 360 (car item)) (SNB:DumpField (cdr item) (1+ depth))))))))
(defun SNB:Describe (ref label / att ext fields field)
  (SNB:Log (strcat "REFERENCE " label " handle=" (vla-get-Handle ref)
    " baseHandle=" (vla-get-Handle (SNB:Attr ref "BASE"))
    " BASE=" (vla-get-TextString (SNB:Attr ref "BASE"))
    " Y=" (rtos (vlax-variant-value (vla-get-Value (SNB:Prop ref "BASE A NIVEL Y"))) 2 8)
    " NIVEL=" (SNB:Value ref)))
  (setq att (SNB:Attr ref "NIVEL")
        ext (cdr (assoc 360 (entget (vlax-vla-object->ename att)))))
  (if (and ext (setq fields (dictsearch ext "ACAD_FIELD"))
           (setq field (dictsearch (cdr (assoc -1 fields)) "TEXT")))
    (SNB:DumpField (cdr (assoc -1 field)) 0)
    (SNB:Check nil (strcat label " retains a live NIVEL field"))))
(defun SNB:Expect (ref expected label)
  (SNB:Check (= expected (SNB:Value ref))
    (strcat label " expected=" expected " actual=" (SNB:Value ref))))
(defun SNB:Insert (x base y / ref)
  (setq ref (vla-InsertBlock (vla-get-ModelSpace SNB:doc)
              (vlax-3d-point (list x 0.0 0.0)) "NIVEL_MM" 1.0 1.0 1.0 0.0))
  (SNB:Base ref base)
  (SNB:Set ref "BASE A NIVEL Y" y)
  (SNB:Evaluate ref)
  ref)
(defun SNB:Cases (/ a b copied negative ref)
  ;; Match the reported order: height evaluated first, then BASE edited alone.
  (SNB:Log "STEP insert zero BASE reference")
  (setq a (SNB:Insert 0.0 "0" 10620.9545))
  (SNB:Expect a "10,621" "initial zero BASE")
  (SNB:Base a "-3")
  (SNB:Log (strcat "BASE_EDIT beforeRegen=" (SNB:Value a)))
  (vla-Regen SNB:doc 1)
  (SNB:Log (strcat "BASE_EDIT afterRegen=" (SNB:Value a)))
  (SNB:Evaluate a)
  (SNB:Expect a "7,621" "reported BASE=-3 Y=10620.9545")
  (SNB:Describe a "reported case")
  (SNB:Log "STEP insert independent reference and copy")
  (setq b (SNB:Insert 5000.0 "100" 10620.9545))
  (SNB:Expect b "110,621" "second reference has independent BASE")
  (setq copied (vla-Copy a))
  (SNB:Base copied "5.25")
  (SNB:Evaluate copied)
  (SNB:Expect copied "15,871" "copy uses its own BASE")
  (SNB:Base a "-10")
  (foreach ref (list a b copied) (SNB:Evaluate ref))
  (SNB:Expect a "0,621" "source BASE changed after copying")
  (SNB:Expect b "110,621" "source edit leaves second reference independent")
  (SNB:Expect copied "15,871" "source edit leaves copied BASE independent")
  (SNB:Describe copied "copied reference")
  (SNB:Base a "-3") (SNB:Evaluate a)
  (SNB:Log "STEP negative Y and zero Y")
  (setq negative (SNB:Insert 10000.0 "-3" -10620.9545))
  (SNB:Expect negative "-13,621" "negative BASE and negative Y")
  (SNB:Set negative "BASE A NIVEL Y" 0.0) (SNB:Evaluate negative)
  (SNB:Expect negative "-3,000" "zero Y preserves BASE")
  (list a b copied negative))
(defun SNB:Cleanup (/ pair)
  (if SNB:db (progn (vl-catch-all-apply 'vlax-release-object (list SNB:db)) (setq SNB:db nil)))
  (if SUB:tempfile (progn (vl-file-delete SUB:tempfile) (setq SUB:tempfile nil)))
  (foreach pair SNB:vars (vl-catch-all-apply 'setvar (list (car pair) (cdr pair))))
  (setq SNB:vars nil))
(defun SNB:Run (phase master report / *error* refs objects source result fresh ref changed broken literal id repairedcopy prefix baseDef item)
  (setq SNB:report (open report "a") SNB:failures 0 SNB:db nil SNB:vars nil
        SUB:tempfile nil SUB:temporary nil
        SNB:doc (vla-get-ActiveDocument (vlax-get-acad-object)))
  (defun *error* (message)
    (SNB:Cleanup)
    (if SNB:report
      (progn
        (SNB:Log (strcat "ERROR " phase " " (if message message "unknown")))
        (SNB:Log (strcat "PHASE_DONE " phase " failures=" (itoa (1+ SNB:failures))))
        (close SNB:report) (setq SNB:report nil)))
    (princ))
  (SNB:Log (strcat "PHASE " phase " drawing=" (getvar "DWGNAME")))
  (if (= phase "IMPORT")
    (progn
      (if (tblsearch "BLOCK" "NIVEL_MM")
        (progn (SNB:Log "ERROR blank fixture already contains NIVEL_MM") (exit)))
      (SNB:Log "STEP create ObjectDBX")
      (setq SNB:db (SUB:Dbx))
      (SNB:Log (strcat "STEP open ObjectDBX source " master))
      (vla-Open SNB:db master)
      (SNB:Log "STEP get source NIVEL_MM record")
      (setq source (vla-Item (vla-get-Blocks SNB:db) "NIVEL_MM")
            objects (vlax-make-safearray vlax-vbObject '(0 . 0)))
      (vlax-safearray-put-element objects 0 source)
      (SNB:Log "STEP copy whole block record")
      (vla-CopyObjects SNB:db objects (vla-get-Blocks SNB:doc))
      (SNB:Log "Imported whole NIVEL_MM block record with ObjectDBX")))
  (SNB:Log "STEP run attribute cases")
  (setq refs (SNB:Cases))
  (if (= phase "IMPORT")
    (progn
      ;; Exercise the production WBLOCK/-INSERT redefinition route without
      ;; touching existing drawings or leaving FILEDIA/ATTREQ in the profile.
      (setq SNB:vars (mapcar '(lambda (v) (cons v (getvar v))) '(FILEDIA ATTREQ)))
      (setvar "FILEDIA" 0) (setvar "ATTREQ" 0)
      ;; Older redefinitions erased the BASE definition referenced by this
      ;; field. A repair must preserve literal prefixes and custom text.
      (setq broken (SNB:Insert 20000.0 "-3" 10620.9545)
            id (vla-GetObjectIdString (vla-get-Utility SNB:doc) broken :vlax-false)
            prefix (if (wcmatch (strcase (getvar "PROGRAM")) "*ZW*") "" "S.F. "))
      ;; AutoCAD parses this expression into native child fields. ZWCAD keeps
      ;; it inline, so retain its imported tree and reproduce loss by erasing
      ;; the original ATTDEF instead of constructing an artificial field.
      (if (/= prefix "")
        (vla-put-TextString (SNB:Attr broken "NIVEL")
          (strcat prefix "%<\\AcExpr (%<\\AcObjProp.16.2 Object(%<\\_ObjId 0>%,1).TextString>%+(%<\\AcObjProp.16.2 Object(%<\\_ObjId "
            id ">%).Parameter(85).UpdatedY \\f \"%lu2%pr8%ds46\">%/1000)) \\f \"%lu2%pr3%ds44\">%")))
      (setq literal (SNB:Insert 25000.0 "-3" 10620.9545))
      (vla-put-TextString (SNB:Attr literal "NIVEL") "TERRENO")
      (vlax-for item (vla-Item (vla-get-Blocks SNB:doc) "NIVEL_MM")
        (if (and (= "AcDbAttributeDefinition" (vla-get-ObjectName item))
                 (= "BASE" (vla-get-TagString item))) (setq baseDef item)))
      (if baseDef (vla-Delete baseDef) (exit))
      (SNB:Evaluate broken)
      (SNB:Describe broken "lost BASE before UPDATEBLOCK")
      (SNB:Log "STEP SUB:Redefine via WBLOCK and INSERT")
      (setq result (SUB:Redefine SNB:doc SNB:db "NIVEL_MM"))
      (SNB:Log "STEP evaluate existing references after redefine")
      (SNB:Check (= 6 result) "UPDATEBLOCK retains all six test references")
      (foreach ref refs (SNB:Evaluate ref))
      (SNB:Expect (nth 0 refs) "7,621" "UPDATEBLOCK reported case")
      (SNB:Expect (nth 1 refs) "110,621" "UPDATEBLOCK second BASE")
      (SNB:Expect (nth 2 refs) "15,871" "UPDATEBLOCK copied BASE")
      (SNB:Expect (nth 3 refs) "-3,000" "UPDATEBLOCK zero Y")
      (SNB:Evaluate broken)
      (SNB:Expect broken (strcat prefix "7,621") "UPDATEBLOCK repairs lost BASE and preserves prefix")
      (SNB:Expect literal "TERRENO" "UPDATEBLOCK preserves literal NIVEL override")
      (SNB:Base broken "-4") (SNB:Evaluate broken)
      (SNB:Expect broken (strcat prefix "6,621") "repaired BASE remains editable")
      (setq repairedcopy (vla-Copy broken))
      (SNB:Base repairedcopy "2") (SNB:Evaluate repairedcopy)
      (SNB:Evaluate broken)
      (SNB:Expect repairedcopy (strcat prefix "12,621") "copy after repair uses its own BASE")
      (SNB:Expect broken (strcat prefix "6,621") "copy after repair leaves source independent")
      (SNB:Describe (car refs) "after UPDATEBLOCK")
      (SNB:Log "STEP fresh insertion after redefine")
      (setq fresh (SNB:Insert 15000.0 "-3" 10620.9545))
      (SNB:Expect fresh "7,621" "new insertion after UPDATEBLOCK")
      (SNB:Describe fresh "new after UPDATEBLOCK")
      (if SUB:tempfile (progn (vl-file-delete SUB:tempfile) (setq SUB:tempfile nil)))
      (vlax-release-object SNB:db)
      (setq SNB:db (SUB:Dbx)) (vla-Open SNB:db master)
      (SNB:Log "STEP repeated UPDATEBLOCK")
      (SUB:Redefine SNB:doc SNB:db "NIVEL_MM")
      (foreach ref (list (car refs) broken repairedcopy fresh) (SNB:Evaluate ref))
      (SNB:Expect (car refs) "7,621" "repeated UPDATEBLOCK keeps repaired BASE")
      (SNB:Expect broken (strcat prefix "6,621") "repeated UPDATEBLOCK preserves prefix")
      (SNB:Expect repairedcopy (strcat prefix "12,621") "repeated UPDATEBLOCK keeps copied BASE")
      (SNB:Expect fresh "7,621" "repeated UPDATEBLOCK repairs newer insertion")))
  (SNB:Cleanup)
  (SNB:Log (strcat "PHASE_DONE " phase " failures=" (itoa SNB:failures)))
  (close SNB:report) (setq SNB:report nil)
  (princ))

(defun SNB:PrepareUndo (master report / *error* source objects ref block pair started changed)
  ;; A separate fixture lets the runner issue U outside this LISP expression,
  ;; immediately after End, without later UPDATEFIELD commands hiding the group.
  (setq SNB:report (open report "a") SNB:failures 0 SNB:db nil
        SNB:vars (mapcar '(lambda (v) (cons v (getvar v))) '(FILEDIA ATTREQ))
        SUB:tempfile nil SUB:temporary nil
        SNB:doc (vla-get-ActiveDocument (vlax-get-acad-object)))
  (defun *error* (message)
    (if started (command-s "_.UNDO" "_End"))
    (SNB:Cleanup)
    (if SNB:report
      (progn
        (SNB:Log (strcat "ERROR UNDO " (if message message "unknown")))
        (SNB:Log (strcat "PHASE_DONE UNDO failures=" (itoa (1+ SNB:failures))))
        (close SNB:report) (setq SNB:report nil)))
    (princ))
  (SNB:Log (strcat "PHASE UNDO drawing=" (getvar "DWGNAME")))
  (if (tblsearch "BLOCK" "NIVEL_MM") (exit))
  (setvar "FILEDIA" 0) (setvar "ATTREQ" 0)
  (setq SNB:db (SUB:Dbx)) (vla-Open SNB:db master)
  (setq source (vla-Item (vla-get-Blocks SNB:db) "NIVEL_MM")
        objects (vlax-make-safearray vlax-vbObject '(0 . 0)))
  (vlax-safearray-put-element objects 0 source)
  (vla-CopyObjects SNB:db objects (vla-get-Blocks SNB:doc))
  (setq ref (SNB:Insert 1234.0 "-3" 10620.9545)
        block (vla-Item (vla-get-Blocks SNB:doc) "NIVEL_MM"))
  (vla-AddCircle block (vlax-3d-point '(700.0 800.0 0.0)) 42.0)
  (setq SNB:undoBefore (SUB:References SNB:doc "NIVEL_MM")
        SNB:undoCount (vla-get-Count block)
        SNB:undoRef ref)
  ;; Commit fixture creation at a LISP expression boundary before opening the
  ;; undo group. ZWCAD can otherwise fold the initial dynamic Y assignment in.
  (SNB:Log "UNDO_FIXTURE_READY")
  (close SNB:report) (setq SNB:report nil)
  (princ))

(defun SNB:RunUndoGroup (report / *error* pair started changed)
  (setq SNB:report (open report "a"))
  (defun *error* (message)
    (if started (command-s "_.UNDO" "_End"))
    (SNB:Cleanup)
    (if SNB:report
      (progn
        (SNB:Log (strcat "ERROR UNDO group " (if message message "unknown")))
        (SNB:Log (strcat "PHASE_DONE UNDO failures=" (itoa (1+ SNB:failures))))
        (close SNB:report) (setq SNB:report nil)))
    (princ))
  (command "_.UNDO" "_Begin") (setq started T)
  (SUB:Redefine SNB:doc SNB:db "NIVEL_MM")
  (SNB:Check (not (equal (caddr (car SNB:undoBefore)) (SUB:Attributes SNB:undoRef)))
    "UNDO fixture exercised BASE field repair")
  (SNB:Check (= (1- SNB:undoCount)
    (vla-get-Count (vla-Item (vla-get-Blocks SNB:doc) "NIVEL_MM")))
    "UNDO fixture replaced obsolete definition")
  ;; Restore variables while the group is still open. From End through U,
  ;; perform only read-only checks, reporting and temporary-file cleanup.
  (foreach pair SNB:vars (setvar (car pair) (cdr pair))) (setq SNB:vars nil)
  (command "_.UNDO" "_End") (setq started nil)
  (SNB:Cleanup)
  (SNB:Log "UNDO_READY")
  (close SNB:report) (setq SNB:report nil)
  (princ))

(defun SNB:CheckUndo (report / *error* row actual prop expected observed same)
  (setq SNB:report (open report "a"))
  (defun *error* (message)
    (if SNB:report
      (progn
        (SNB:Log (strcat "ERROR UNDO check " (if message message "unknown")))
        (SNB:Log (strcat "PHASE_DONE UNDO failures=" (itoa (1+ SNB:failures))))
        (close SNB:report) (setq SNB:report nil)))
    (princ))
  (SNB:Check (= SNB:undoCount
    (vla-get-Count (vla-Item (vla-get-Blocks SNB:doc) "NIVEL_MM")))
    "U restores obsolete definition")
  (foreach row SNB:undoBefore
    (SNB:Check (equal (cadr row) (SUB:Placement (car row)) 1e-8)
      "U restores NIVEL_MM handle and placement")
    (SNB:Check (equal (caddr row) (SUB:Attributes (car row)))
      "U restores original BASE value, attribute handles and field links")
    (setq actual (SUB:Dynamic (car row)))
    (foreach prop (cadddr row)
      (setq expected (vlax-variant-value (cdr prop))
            observed (if (assoc (car prop) actual)
              (vlax-variant-value (cdr (assoc (car prop) actual))))
            same (equal expected observed 1e-8))
      (if (not same)
        (SNB:Log (strcat "UNDO_VALUE " (car prop)
          " expected=" (if (numberp expected) (rtos expected 2 12) (vl-princ-to-string expected))
          " actual=" (if (numberp observed) (rtos observed 2 12) (vl-princ-to-string observed))
          " difference=" (if (and (numberp expected) (numberp observed))
            (rtos (- observed expected) 2 12) "n/a"))))
      ;; Reproduced with the original updater too: ZWCAD 2026 resets dynamic
      ;; Y when undoing a native redefinition. Keep this limitation visible.
      (if (and (not same) (wcmatch (strcase (getvar "PROGRAM")) "*ZW*")
               (= "BASE A NIVEL Y" (car prop)) (equal observed 0.0))
        (SNB:Log "KNOWN_LIMITATION ZWCAD 2026 native redefine undo resets dynamic Y (also reproduced before this fix)")
        (SNB:Check same
          (strcat "U restores dynamic property " (car prop))))))
  (SNB:Log (strcat "PHASE_DONE UNDO failures=" (itoa SNB:failures)))
  (close SNB:report) (setq SNB:report nil)
  (princ))
(princ)

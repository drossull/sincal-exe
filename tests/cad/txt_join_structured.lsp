;;; Load after txt_join_regression.lsp, in a disposable drawing.
(defun TXUT:Info (text / r)
  (setq r (TXUT:Record text 0.0 0.0))
  (TXU:RowInfo (list r) 0.35 1.0))

(defun TXUT:Structured (/ head children paras built rows r a b text source mt ref point)
  (TXUT:Assert (equal (TXU:Prefix "10.CONTRAFLECHA: 3,37 cm.") '("10." "CONTRAFLECHA: 3,37 cm.")) "number glued to heading")
  (TXUT:Assert (null (TXU:Prefix "1.2 mm")) "decimal is not a list label")
  (TXUT:Assert (null (TXU:Prefix "421-18")) "standard number is not a list label")
  (TXUT:Assert (= (TXU:Units "450 kg/cm2 y 1,4 cm2") "450 kg/cm{\\H0.7x;\\S2^;} y 1,4 cm{\\H0.7x;\\S2^;}") "exponents kept and formatted")
  (TXUT:Assert (= (TXU:Units "ASTM2 m20") "ASTM2 m20") "unit formatter respects word boundaries")
  (setq head (TXUT:Info "1. HORMIGON:")
        children (mapcar 'TXUT:Info '("RESISTENCIA INICIAL: 450 kg/cm2" "RESISTENCIA FINAL: 500" "ARIDO MAXIMO 2.0 cm.")))
  (setq paras (TXU:Group head children T))
  (TXUT:Assert (equal (mapcar '(lambda (p) (cdr (assoc 'label p))) paras) '("1." "1.1." "1.2." "1.3.")) "inferred child hierarchy")
  (TXUT:Assert (equal (mapcar '(lambda (p) (cdr (assoc 'label p))) (TXU:Group head children nil)) '("1." nil nil nil)) "inference can be disabled")
  (setq paras (TXU:Group (TXUT:Info "3. ACERO:") (mapcar 'TXUT:Info
    '("CABLES: SECCION 1,4 cm2." "DEBE CUMPLIR CON LAS SIGUIENTES NORMAS:" "ASTM A 421-18" "ASTM A 416-18.")) T))
  (TXUT:Assert (equal (mapcar '(lambda (p) (cdr (assoc 'label p))) paras)
    '("3." "3.1." "3.2." "3.2.1." "3.2.2.")) "nested standards hierarchy")
  (setq paras (TXU:Hierarchy (mapcar 'TXUT:Info '("1. TITULO:" "1.4. EXISTENTE" "1.4.2. EXISTENTE")) T))
  (TXUT:Assert (equal (mapcar '(lambda (p) (cdr (assoc 'label p))) paras) '("1." "1.4." "1.4.2.")) "existing numbering never renumbered")
  (TXUT:Assert (equal (mapcar '(lambda (p) (cdr (assoc 'level p))) paras) '(0 1 2)) "existing nesting indented")
  (setq paras (TXU:Group (TXUT:Info "7. CORTE:") (list (TXUT:Info "SE PROCEDERA A CORTAR CON DISCO.")) T))
  (TXUT:Assert (and (= 1 (length paras)) (= (cdr (assoc 'text (car paras))) "CORTE: SE PROCEDERA A CORTAR CON DISCO.")) "single heading continuation merged")
  (setq paras (TXU:Group (TXUT:Info "6. FUNDAS:") (mapcar 'TXUT:Info '("DIAMETRO: 19 mm." "ESPESOR: 2 mm." "CALIDAD: VIRGEN.")) T))
  (TXUT:Assert (equal (mapcar '(lambda (p) (cdr (assoc 'label p))) paras) '("6." nil nil nil)) "short field list remains unnumbered")
  (setq rows (list (list (TXUT:Record "1. RESISTENCIA: 450 kg/cm2" 0.0 20.0))
                   (list (TXUT:Record "RESISTENCIA A LOS 28 DIAS: 500" 0.0 18.5))))
  (TXUT:Assert (= 2 (length (TXU:Paragraphs rows 0.35 1.0 0.0))) "independent colon statements not merged")
  (setq rows (list (list (TXUT:Record "9. CONSERVANDO SU VERTICALIDAD TODO EL" 0.0 20.0))
                   (list (TXUT:Record "TIEMPO." 2.0 18.5))))
  (TXUT:Assert (= "9. CONSERVANDO SU VERTICALIDAD TODO EL TIEMPO."
    (cdr (assoc 'text (car (TXU:Paragraphs rows 0.35 1.0 0.0))))) "wrapped continuation becomes one paragraph")
  (setq rows (list (list (TXUT:Record "CABLES: 1.970.000 kg/cm2DEBE CUMPLIR CON LAS SIGUIENTES NORMAS:" 0.0 20.0))))
  (setq paras (TXU:Paragraphs rows 0.35 1.0 0.0))
  (TXUT:Assert (and (= 2 (length paras)) (TXU:Ends (cdr (assoc 'text (car paras))) "kg/cm2")) "normative split preserves exponent")
  (setq a (TXUT:Record "11380 cm" 0.0 20.0) b (TXUT:Record "19,93 t." 20.0 20.0))
  (setq rows (list (list a b) (list (TXUT:Record "20000 cm" 0.0 18.5) (TXUT:Record "19,93 t." 20.0 18.5))))
  (setq text (TXU:Structured rows 0.35 1.0 0.0 T))
  (TXUT:Assert (and (vl-string-search "\t" text) (not (vl-string-search "\\~" text))) "table uses tabs not padding spaces")
  (TXUT:Assert (equal (caar (cdr (assoc 'cells (TXU:RowInfo (car rows) 0.35 1.0))))
    (caar (cdr (assoc 'cells (TXU:RowInfo (cadr rows) 0.35 1.0)))) 1.0e-9) "column alignment independent of first glyph")
  (setq ref (nth 8 a) mt (TXU:CreateWidth ref '(100.0 0.0 0.0) text 1.0 60.0))
  (TXUT:Assert (equal (cdr (assoc 41 (entget mt))) 60.0 1.0e-8) "MTEXT reflow width applied")
  (TXUT:Assert (= text (TXUT:Content mt)) "native paragraph and tab codes roundtrip")
  (princ (strcat "\nTXT-JOIN_STRUCTURED_FAILURES=" (itoa TXUT:Failures) "\n"))
  (princ))
(TXUT:Structured)

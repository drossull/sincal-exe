;;; Load SINCALISP.lsp first. This test does not open the modal dialog.
(setq SCLT:failures 0)
(defun SCLT:Assert (ok label)
  (if (not ok) (setq SCLT:failures (1+ SCLT:failures)))
  (princ (strcat "\nSINCALISP-TEST " (if ok "PASS " "FAIL ") label)))
(setq SCLT:rows (SCL:Rows ""))
(SCLT:Assert (= (length SCLT:rows) (length (SCL:Catalog))) "all entries")
(SCLT:Assert (equal (mapcar 'car SCLT:rows) (acad_strlsort (mapcar 'car (SCL:Catalog)))) "alphabetical")
(SCLT:Assert (equal (SCL:Rows "romand") (SCL:Rows "ROMAND")) "case insensitive")
(SCLT:Assert (= 1 (length (SCL:Rows "romand.shx"))) "description search")
(SCLT:Assert (= 1 (length (SCL:Rows "lisps/ZV.lsp"))) "filename search")
(SCLT:Assert (not (SCL:Rows "not-a-sincal-command-98765")) "no results")
(SCLT:Assert (not (SCL:Rows "*")) "literal search, not wildcards")
(SCLT:Assert (assoc "DUPLICAR" SCLT:rows) "aliases included")
(SCLT:Assert (assoc "C0" SCLT:rows) "startup commands included")
(princ (strcat "\nSINCALISP-TEST DONE failures=" (itoa SCLT:failures)))
(princ)

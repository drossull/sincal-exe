;;; Run only in a disposable blank drawing, after loading ROMAND.lsp.
(setq SRDT:failures 0)
(if (not SRDT:report) (setq SRDT:report (getenv "SINCAL_ROMAND_REPORT")))
(defun SRDT:Log (text / out)
  (princ (strcat "\n" text))
  (if SRDT:report
    (progn (setq out (open SRDT:report "a")) (write-line text out) (close out))))
(defun SRDT:Assert (ok label)
  (if (not ok) (setq SRDT:failures (1+ SRDT:failures)))
  (SRDT:Log (strcat "ROMAND-TEST " (if ok "PASS " "FAIL ") label)))
(defun *error* (msg)
  (SRDT:Log (strcat "ROMAND-TEST FAIL runtime: " msg))
  (SRDT:Log "ROMAND-TEST DONE failures=1") (princ))
(vl-load-com)
(setvar "TILEMODE" 1)
(setq SRDT:standard (entget (tblobjname "STYLE" "Standard") '("*")))
(setq SRDT:echo (getvar "CMDECHO"))
(SRD:Run nil)
(SRDT:Assert (SRD:Valid) "create all screenshot settings")
(setq SRDT:styleobj (vl-catch-all-apply 'vlax-ename->vla-object (list (tblobjname "STYLE" "RomanD"))))
(if (not (vl-catch-all-error-p SRDT:styleobj))
  (progn
    (vla-GetFont SRDT:styleobj 'SRDT:face 'SRDT:bold 'SRDT:italic 'SRDT:charset 'SRDT:pitch)
    (SRDT:Log (strcat "FONT " (vl-princ-to-string (list SRDT:face SRDT:bold SRDT:italic SRDT:pitch (vla-get-FontFile SRDT:styleobj)))))
    (SRDT:Assert (= (strcase SRDT:face) "ROMAND") "TrueType typeface is RomanD")))
(SRDT:Assert (= (strcase (getvar "TEXTSTYLE")) "ROMAND") "current style")
(setq SRDT:handle (tblobjname "STYLE" "RomanD"))
(SRD:Run nil)
(SRDT:Assert (and (SRD:Valid) (eq SRDT:handle (tblobjname "STYLE" "RomanD"))) "idempotent, same style")
;; Legacy SHX style with wrong layout orientation and all three effects.
(command-s "_.-STYLE" "RomanD" "romand.shx" "_Annotative" "_Yes" "_Yes" 7.0 1.2 12.0 "_Yes" "_Yes" "_Yes")
(SRDT:Assert (not (SRD:Valid)) "reject wrong configuration")
(SRD:Run nil)
(SRDT:Assert (SRD:Valid) "convert legacy SHX to TrueType and repair annotation")
(entmod (SRD:Put 3 "txt.shx" (entget (tblobjname "STYLE" "RomanD"))))
(SRD:Run nil)
(SRDT:Assert (SRD:Valid) "repair different font")
(SRDT:Assert (equal SRDT:standard (entget (tblobjname "STYLE" "Standard") '("*"))) "other styles unchanged")
(SRDT:Assert (= SRDT:echo (getvar "CMDECHO")) "CMDECHO restored")

;; New objects use a private, nonannotative style so other drawing styles
;; and existing entities are irrelevant to these checks (scratch DWG only).
(command-s "_.-STYLE" "SRDT_PLAIN" "txt.shx" 0.0 1.0 0.0 "_No" "_No" "_No")
(command "_.-SCALELISTEDIT" "_Add" "SRDT_1_100" "1:100" "_Exit")
(setvar "CANNOSCALE" "SRDT_1_100")
(defun SRDT:Text (name point justify / en)
  (setq en (entmakex (list '(0 . "TEXT") '(8 . "0") '(7 . "SRDT_PLAIN")
    (cons 1 name) (cons 10 point) (cons 11 point) '(40 . 7.0) '(41 . 1.6)
    '(50 . 0.3) '(51 . 0.2) '(71 . 2) (cons 72 justify) '(73 . 0))))
  (entupd en) en)
(setq SRDT:plain (SRDT:Text "Conservar 123" '(10.0 20.0 0.0) 0)
      SRDT:right (SRDT:Text "Derecha" '(400.0 20.0 0.0) 2)
      SRDT:untouched (SRDT:Text "Sin seleccionar" '(10.0 60.0 0.0) 0)
      SRDT:before (entget SRDT:untouched)
      SRDT:point (cdr (assoc 10 (entget SRDT:plain)))
      SRDT:rightpoint (cdr (assoc 11 (entget SRDT:right)))
      SRDT:raw "{\\fArial|b1;\\H3x;\\W2;\\Q12;Titulo}\\P\\C3;Linea \\S1/2; \\\\Hliteral"
      SRDT:clean "{Titulo}\\P\\C3;Linea \\S1/2; \\\\Hliteral"
      SRDT:mtext (entmakex (list '(0 . "MTEXT") '(100 . "AcDbEntity") '(8 . "0")
        '(100 . "AcDbMText") '(7 . "SRDT_PLAIN") '(10 20.0 100.0 0.0)
        '(40 . 7.0) '(41 . 1200.0) '(71 . 1) (cons 1 SRDT:raw)))
      SRDT:ss (ssadd))
(setq SRDT:field (entmakex '((0 . "MTEXT") (100 . "AcDbEntity") (8 . "0")
  (100 . "AcDbMText") (7 . "SRDT_PLAIN") (10 10.0 200.0 0.0)
  (40 . 7.0) (41 . 1200.0) (71 . 1) (1 . "field"))))
(setq SRDT:fieldobj (vl-catch-all-apply 'vlax-ename->vla-object (list SRDT:field)))
(if (vl-catch-all-error-p SRDT:fieldobj) (setq SRDT:fieldobj nil))
(if SRDT:fieldobj
  (progn
    (setq SRDT:line (entmakex '((0 . "LINE") (10 0.0 0.0 0.0) (11 100.0 0.0 0.0)))
          SRDT:lineobj (vlax-ename->vla-object SRDT:line)
          SRDT:util (vla-get-Utility (vla-get-ActiveDocument (vlax-get-acad-object)))
          SRDT:id (vla-GetObjectIdString SRDT:util SRDT:lineobj :vlax-false))
    (vla-put-TextString SRDT:fieldobj (strcat
      "{\\fArial;\\H2x;\\W2;\\Q12;Valor %<\\AcExpr (2+3) \\f \"%lu2%pr0\">%}\\P"
      "Largo %<\\AcObjProp Object(%<\\_ObjId " SRDT:id ">%).Length \\f \"%lu2%pr0\">%"))
    (setq SRDT:fieldcode (vla-FieldCode SRDT:fieldobj)
          SRDT:fieldbefore (entget SRDT:field '("*")))
    (SRDT:Assert (and (SRD:HasFields (entget SRDT:field)) SRDT:fieldcode) "field fixture is live"))
  (SRDT:Log "ROMAND-TEST SKIP ActiveX fields unavailable in Core Console"))
(foreach en (list SRDT:plain SRDT:right SRDT:mtext SRDT:field) (ssadd en SRDT:ss))
(SRD:Run SRDT:ss)
(setq SRDT:data (entget SRDT:plain '("*")))
(SRDT:Assert (and (= (cdr (assoc 7 SRDT:data)) "RomanD")
  (= (cdr (assoc 1 SRDT:data)) "Conservar 123")
  (equal (cdr (assoc 10 SRDT:data)) SRDT:point 1e-8)
  (equal (cdr (assoc 50 SRDT:data)) 0.3 1e-8)) "TEXT content position rotation preserved")
(SRDT:Assert (and (equal (cdr (assoc 40 SRDT:data)) 250.0 1e-8)
  (equal (cdr (assoc 41 SRDT:data)) 0.8 1e-8)
  (equal (cdr (assoc 51 SRDT:data)) 0.0 1e-8)
  (= (cdr (assoc 71 SRDT:data)) 0)
  (= (SRD:Flag SRDT:data "AcadAnnotative") 1)) "TEXT paper height width effects annotation")
(SRDT:Assert (equal (cdr (assoc 11 (entget SRDT:right))) SRDT:rightpoint 1e-8)
  "justified TEXT anchor preserved")
(setq SRDT:data (entget SRDT:mtext '("*")))
(SRDT:Assert (and (= (cdr (assoc 7 SRDT:data)) "RomanD")
  (= (SRD:RawText SRDT:data) SRDT:clean)
  (equal (cdr (assoc 10 SRDT:data)) '(20.0 100.0 0.0) 1e-8)
  (equal (cdr (assoc 41 SRDT:data)) 1200.0 1e-8)
  (equal (cdr (assoc 40 SRDT:data)) 250.0 1e-8)
  (= (cdr (assoc 71 SRDT:data)) 1)) "MTEXT formatting content anchor attachment width")
(SRDT:Assert (equal SRDT:before (entget SRDT:untouched)) "unselected text unchanged")
(if SRDT:fieldobj (SRDT:Assert (and (SRD:HasFields (entget SRDT:field))
  (= (vla-FieldCode SRDT:fieldobj) (SRD:UniformMText SRDT:fieldcode))
  (= (cdr (assoc 7 (entget SRDT:field))) "RomanD")
  (equal (cdr (assoc 10 (entget SRDT:field))) '(10.0 200.0 0.0) 1e-8))
  "MTEXT fields formatted with live formula and same anchor"))
(if SRDT:fieldobj (progn
  (vla-put-EndPoint SRDT:lineobj (vlax-3d-point '(175.0 0.0 0.0)))
  (command "_.UPDATEFIELD" SRDT:field "")
  (SRDT:Assert (and (vl-string-search "175" (vla-get-TextString SRDT:fieldobj))
    (= (vla-FieldCode SRDT:fieldobj) (SRD:UniformMText SRDT:fieldcode)))
    "linked length updates from 100 to 175 after ROMAND")
  (SRD:Run (ssadd SRDT:field))
  (SRDT:Assert (and (vl-string-search "175" (vla-get-TextString SRDT:fieldobj))
    (= (vla-FieldCode SRDT:fieldobj) (SRD:UniformMText SRDT:fieldcode)))
    "repeated ROMAND retains live links")))
(SRDT:Log (strcat "ROMAND-TEST DONE failures=" (itoa SRDT:failures)))
(princ)
